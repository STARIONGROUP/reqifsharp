# Subset026

# Specification: Specification Document
- Description: Subset026

## 3 (Requirement Type)
System Requirements Specification
Chapter 3
Principles
- WordTraceId: 16
- atomic: true
- Legal Obligation: unknown
- implement: false
- kind: Heading

### 3.1 (Requirement Type)
Modification History
- WordTraceId: 134
- atomic: false
- Legal Obligation: not applicable
- implement: true
- kind: ordinary

### 3.1[2] (Requirement Type)
- WordTraceId: 155
- atomic: false
- Legal Obligation: not applicable
- implement: false
- kind: Placeholder

#### 3.1[2].[t]* (Requirement Type)
| Issue Number Date | Section Number | Modification / Description | Author/Editor |
| --- | --- | --- | --- |
| 1.0.1 990307 | All | Merge of Basic + Detailed Principles Removing redundant material, correcting text and adding proposals. | HE |
| 1.1.0 990423 | All | Class P Official Issue | HE |
| 1.1.1 990521 | All | Corrections after UNISIG review. | KL |
| 1.1.2 990713 | All | Additional functions for class 1 and changes related to these functions in other parts | KL |
| 1.1.3 990722 | All | Changes according to review of version 1.1.2 | KL |
| 1.1.4 990729 | All | Editorial corrections, finalisation meeting Stuttgart 990729 | HE |
| 1.2.0 990730 | Version number | Release version | HE |
| 1.3.0 991201 | All | Corrections and new functions according to ECSAG and UNISIG comments | KL |
| 1.3.1 991217 | All | Corrections after UNISIG review 15 December 99 | KL |
| 2.0.0 991222 | Minor editing | Release Version | Ch. Frerichs (ed.) |
| 2.0.1 000921 | All | Corrections after UNISIG review 15 June 00 | KL |
| 2.1.0 001017 | Most | Corrections after UNISIG review 11 October 00 | KL |
| 2.2.0 010108 | Section 3.18.4.6.6 – 3.18.4.6.8 removed | Changes as decided on Steering Committee meeting 13 December 2000 (changes from 2.0.0 marked) | KL |
| 2.2.2 020201 | Refer to document: SUBSET–026 Corrected Paragraphs, Issue 2.2.2 |  | KL |
| 2.2.4 SG checked 040528 | Including all CLRs agreed with the EEIG (see “List of CLRs agreed with EEIG for SRS v2.2.4” dated 28/05/04) Affected clauses see change marks |  | H. Kast |
| 2.2.5 210105 | Incorporation of solution proposal for CLR 007 with EEIG users group comments Corrections according to erratum list agreed in SG meeting 170105 |  | AH |
| 2.2.6 050301 | Including all CLRs being in state “EEIG pending” as per list of CLRs extracted on 28/01/05. |  | OG |
| 2.2.7 220705 | Including all CLRs extracted from “CR-Report_10.6.05-by number.rtf” and mentioned in column 2.2.7 in “CR status 13.6.05.xls” 22/07/05 Changes for CR 126 included (HK) |  | OG |
| 2.2.8 211105 | Change marks cleaned up and updated according to last CRs decisions (including split of CRs7&126) |  | OG |
| 2.2.9 24/02/06 | Including all CRs that are classified as “IN” as per SUBSET-108 version 1.0.0 Removal of all CRs that are not classified as “IN” as per SUBSET-108 version 1.0.0, with the exception of CRs 63,98,120,158,538 |  | OG |
| 2.3.0 24/02/06 | Release version |  | HK |
| 2.3.1 12/06/06 |  |  | OG |
| 2.3.2 17/03/08 | Including all CRs that are classified as “IN” as per SUBSET-108 version 1.2.0 and all CRs that are in state “Analysis completed” according to ERA CCM |  | AH |
| 2.9.1 06/10/08 | Including all enhancement CR’s retained for baseline 3 and all other error CR’s For editorial reasons, the following CR’s are also included: CR656, CR804, CR821 |  | AH |
| 3.0.0 13/12/08 | Release version |  | AH |
| 3.0.1 22/12/09 | Including the results of the editorial review of the SRS 3.0.0 and the other error CR’s that are in state “Analysis completed” according to ERA CCM |  | AH |
| 3.1.0 22/02/10 | Release version |  | AH |
| 3.1.1 08/11/10 | Including all CR’s that are in state “Analysis completed” according to ERA CCM, plus CR731, 972 and 1000. |  | AH |
| 3.2.0 22/12/10 | Release version |  | AH |
| 3.2.1 13/12/11 | Including all CR’s that are in state “Analysis completed” according to ERA CCM, plus CR772 |  | AH |
| 3.3.0 07/03/12 | Baseline 3 release version |  | AH |
- WordTraceId: 3275
- atomic: false
- Legal Obligation: not applicable
- implement: false
- kind: Table

### 3.2 (Requirement Type)
Table of Contents
- WordTraceId: 3275
- atomic: false
- Legal Obligation: not applicable
- implement: true
- kind: ordinary

### 3.3 (Requirement Type)
Introduction
- WordTraceId: 11430
- atomic: false
- Legal Obligation: not applicable
- implement: false
- kind: Heading

#### 3.3.1 (Requirement Type)
Scope and purpose
- WordTraceId: 11443
- atomic: false
- Legal Obligation: not applicable
- implement: false
- kind: Heading

##### 3.3.1.1 (Requirement Type)
The chapter 3, Principles, specifies the system principles of ETCS/ERTMS. These principles apply to on-board and trackside subsystems and are mainly derived from FRS.
- WordTraceId: 11461
- atomic: false
- Legal Obligation: unknown
- implement: true
- implementerEnhanced: The chapter 3, Principles, specifies the system principles of ETCS/ERTMS. These principles apply to on-board and
  trackside
  [EXTERNAL]
  subsystems and are mainly derived from FRS.
- kind: ordinary

##### 3.3.1.2 (Requirement Type)
The principles define the operational and technical behaviour of the system in general and functional terms.
- WordTraceId: 11629
- atomic: true
- Legal Obligation: unknown
- implement: true
- kind: ordinary

##### 3.3.1.3 (Requirement Type)
The chapter is divided into subchapters. In each subchapter normally several requirements are defined. Each requirement is identified with a unique identification number.
- WordTraceId: 11740
- atomic: false
- Legal Obligation: unknown
- implement: true
- kind: ordinary

##### 3.3.1.4 (Requirement Type)
Notes, Justifications and Examples are only informative and shall not be regarded as requirements.
- WordTraceId: 11911
- atomic: true
- Legal Obligation: mandatory
- implement: false
- kind: Definition

### 3.4 (Requirement Type)
Balise configuration and linking
- WordTraceId: 12010
- atomic: false
- Legal Obligation: not applicable
- implement: false
- implementerEnhanced: Balise
  [EXTERNAL]
  configuration and linking
- kind: Heading

#### 3.4.1 (Requirement Type)
Balise Configurations – Balise Group Definition
- WordTraceId: 12043
- atomic: false
- Legal Obligation: not applicable
- implement: false
- implementerEnhanced: Balise
  [EXTERNAL]
  Configurations –
  Balise Group
  [EXTERNAL]
  Definition
- kind: Heading

##### 3.4.1.1 (Requirement Type)
A balise group shall consist of between one and eight balises.
- WordTraceId: 12091
- atomic: true
- Legal Obligation: mandatory
- implement: true
- implementerEnhanced: A
  balise group
  [EXTERNAL]
  shall consist of between one and eight
  balises
  [EXTERNAL]
  .
- kind: ordinary

##### 3.4.1.2 (Requirement Type)
In every balise shall at least be stored:
- WordTraceId: 12154
- atomic: true
- Legal Obligation: mandatory
- implement: true
- implementerEnhanced: In every
  balise
  [EXTERNAL]
  shall
  at least
  [WEAK]
  be stored:
- kind: ordinary

###### 3.4.1.2.a (Requirement Type)
The internal number (from 1 to 8) of the balise
- WordTraceId: 12196
- atomic: true
- Legal Obligation: unknown
- implement: true
- implementerEnhanced: The internal number (from 1 to 8) of the
  balise
  [EXTERNAL]
- ListNumberText: a)
- kind: ordinary

###### 3.4.1.2.b (Requirement Type)
The number of balises inside the group
- WordTraceId: 12244
- atomic: true
- Legal Obligation: unknown
- implement: true
- implementerEnhanced: The number of
  balises
  [EXTERNAL]
  inside the group
- ListNumberText: b)
- kind: ordinary

###### 3.4.1.2.c (Requirement Type)
The balise group identity.
- WordTraceId: 12283
- atomic: true
- Legal Obligation: unknown
- implement: true
- implementerEnhanced: The
  balise group
  [EXTERNAL]
  identity.
- ListNumberText: c)
- kind: ordinary

##### 3.4.1.3 (Requirement Type)
The internal number of the balise describes the relative position of the balise in the group.
- WordTraceId: 12310
- atomic: true
- Legal Obligation: unknown
- implement: false
- implementerEnhanced: The internal number of the
  balise
  [EXTERNAL]
  describes the relative position of the
  balise
  [EXTERNAL]
  in the group.
- kind: Definition

#### 3.4.2 (Requirement Type)
Balise Co-ordinate System
- WordTraceId: 12404
- atomic: false
- Legal Obligation: not applicable
- implement: false
- implementerEnhanced: Balise
  [EXTERNAL]
  Co-ordinate System
- kind: Heading

##### 3.4.2.1 (Requirement Type)
PLACEHOLDER REQUIREMENT - DO NOT TRACE
- WordTraceId: 12430
- atomic: false
- Legal Obligation: not applicable
- implement: false
- kind: Placeholder

###### 3.4.2.1.1 (Requirement Type)
Every balise group has its own co-ordinate system.
- WordTraceId: 12430
- atomic: true
- Legal Obligation: unknown
- implement: true
- implementerEnhanced: Every
  balise group
  [EXTERNAL]
  has its own co-ordinate system.
- kind: ordinary

###### 3.4.2.1.2 (Requirement Type)
The orientation of the co-ordinate system of a balise group (i.e., nominal or reverse direction) is identified as balise group orientation.
- WordTraceId: 12481
- atomic: true
- Legal Obligation: unknown
- implement: true
- implementerEnhanced: The orientation of the co-ordinate system of a
  balise group
  [EXTERNAL]
  (i.e., nominal or reverse direction) is identified as
  balise group
  [EXTERNAL]
  orientation.
- kind: ordinary

##### 3.4.2.2 (Requirement Type)
Balise groups composed of two or more balises
- WordTraceId: 12621
- atomic: false
- Legal Obligation: not applicable
- implement: false
- implementerEnhanced: Balise groups
  [EXTERNAL]
  composed of two or more
  balises
  [EXTERNAL]
- kind: Heading

###### 3.4.2.2.1 (Requirement Type)
The origin of the co-ordinate system for each balise group shall be given by the balise number 1 (called location reference) in the balise group.
- WordTraceId: 12667
- atomic: true
- Legal Obligation: mandatory
- implement: true
- implementerEnhanced: The origin of the co-ordinate system
  for each
  [LOOP]
  balise group
  [EXTERNAL]
  shall be given by the
  balise
  [EXTERNAL]
  number 1 (called location reference) in the
  balise group
  [EXTERNAL]
  .
- kind: ordinary

###### 3.4.2.2.2 (Requirement Type)
The nominal direction of each balise group is defined by increasing internal balise numbers.
- WordTraceId: 12813
- atomic: true
- Legal Obligation: unknown
- implement: true
- implementerEnhanced: The nominal direction of each
  balise group
  [EXTERNAL]
  is defined by increasing internal
  balise
  [EXTERNAL]
  numbers.
- kind: ordinary

###### 3.4.2.2.2[2] (Requirement Type)
- WordTraceId: 12906
- atomic: false
- Legal Obligation: not applicable
- implement: false
- kind: Placeholder

###### 3.4.2.2.2[2].[f]1 (Requirement Type)
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- WordTraceId: 12931
- atomic: false
- Legal Obligation: not applicable
- implement: false
- kind: Figure

###### 3.4.2.2.2[2].[f]1.C (Requirement Type)
Figure {Figure 1}: Orientation of the balise group
- WordTraceId: 12931
- atomic: true
- Legal Obligation: unknown
- PlainText: Figure 1: Orientation of the balise group
- implement: false
- implementerEnhanced: Figure 1: Orientation of the
  balise group
  [EXTERNAL]
- kind: Figure

##### 3.4.2.3 (Requirement Type)
Balise groups composed of a single balise
- WordTraceId: 12998
- atomic: false
- Legal Obligation: not applicable
- implement: false
- implementerEnhanced: Balise groups
  [EXTERNAL]
  composed of a single
  balise
  [EXTERNAL]
- kind: Heading

###### 3.4.2.3.1 (Requirement Type)
Note: Balise groups consisting of only one single balise are referred to as "single balise groups" in the following.
- WordTraceId: 13040
- atomic: false
- Legal Obligation: not applicable
- implement: false
- implementerEnhanced: Note:
  Balise groups
  [EXTERNAL]
  consisting of only one single
  balise
  [EXTERNAL]
  are referred to as "single
  balise groups
  [EXTERNAL]
  " in the following.
- kind: Note

###### 3.4.2.3.1[2] (Requirement Type)
- WordTraceId: 13157
- atomic: false
- Legal Obligation: not applicable
- implement: false
- kind: Placeholder

###### 3.4.2.3.1[2].[f]1a (Requirement Type)
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- WordTraceId: 13182
- atomic: false
- Legal Obligation: not applicable
- implement: false
- kind: Figure

###### 3.4.2.3.1[2].[f]1a.C (Requirement Type)
Figure 1a: Single balise group
- WordTraceId: 13182
- atomic: true
- Legal Obligation: unknown
- implement: false
- implementerEnhanced: Figure 1a: Single
  balise group
  [EXTERNAL]
- kind: Figure

###### 3.4.2.3.2 (Requirement Type)
Level 1:
- WordTraceId: 13213
- atomic: false
- Legal Obligation: not applicable
- implement: false
- kind: Heading

###### 3.4.2.3.2.1 (Requirement Type)
The assignment of the co-ordinate system shall be by means of linking data.
- WordTraceId: 13222
- atomic: true
- Legal Obligation: mandatory
- implement: true
- kind: ordinary

###### 3.4.2.3.2.2 (Requirement Type)
For balise groups consisting of a single balise, the information "direction with which the linked balise group will be passed over" received from a previous balise group shall assign a co-ordinate system to the balise.
- WordTraceId: 13298
- atomic: true
- Legal Obligation: mandatory
- implement: true
- implementerEnhanced: For
  balise groups
  [EXTERNAL]
  consisting of a single
  balise
  [EXTERNAL]
  , the information "direction with which the linked
  balise group
  [EXTERNAL]
  will be passed over" received from a previous
  balise group
  [EXTERNAL]
  shall assign a co-ordinate system to the
  balise
  [EXTERNAL]
  .
- kind: ordinary

###### 3.4.2.3.2.2[2] (Requirement Type)
- WordTraceId: 13518
- atomic: false
- Legal Obligation: not applicable
- implement: false
- kind: Placeholder

###### 3.4.2.3.2.2[2].[f]2 (Requirement Type)
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- WordTraceId: 13546
- atomic: false
- Legal Obligation: not applicable
- implement: false
- kind: Figure

###### 3.4.2.3.2.2[2].[f]2.C (Requirement Type)
Figure {Figure 2}: Assignment of a co-ordinate system to a single balise group by linking
- WordTraceId: 13546
- atomic: true
- Legal Obligation: unknown
- PlainText: Figure 2: Assignment of a co-ordinate system to a single balise group by linking
- implement: false
- implementerEnhanced: Figure 2: Assignment of a co-ordinate system to a single
  balise group
  [EXTERNAL]
  by linking
- kind: Figure

###### 3.4.2.3.2.3 (Requirement Type)
The reference for the linking data shall be either a single balise group if a co-ordinate system has been assigned to it before, or a balise group consisting of two or more balises (with "inherent" co-ordinate system)
- WordTraceId: 13652
- atomic: true
- Legal Obligation: mandatory
- implement: true
- implementerEnhanced: The reference for the linking data shall be either a single
  balise group
  [EXTERNAL]
  if
  [CONDITION]
  a co-ordinate system has been assigned to it before, or a
  balise group
  [EXTERNAL]
  consisting of two or more
  balises
  [EXTERNAL]
  (with "inherent" co-ordinate system)
- kind: ordinary

###### 3.4.2.3.3 (Requirement Type)
Level 2/3:
- WordTraceId: 13870
- atomic: false
- Legal Obligation: not applicable
- implement: false
- kind: Heading

###### 3.4.2.3.3.1 (Requirement Type)
If the ERTMS/ETCS on-board equipment cannot evaluate the orientation of the last balise group detected, being a single balise group, i.e. no linking information is available to identify the orientation of the co-ordinate system of this single balise group, the ERTMS/ETCS on-board equipment shall report its position by means of a position report based on two balise groups reporting the train position in reference to the LRBG and the “previous LRBG”, if any.
- WordTraceId: 13881
- atomic: true
- Legal Obligation: mandatory
- implement: true
- implementerEnhanced: If
  [CONDITION]
  the
  ERTMS/ETCS on-board equipment
  [SELF]
  cannot evaluate the orientation of the last
  balise group
  [EXTERNAL]
  detected, being a single
  balise group
  [EXTERNAL]
  , i.e. no linking information is available to identify the orientation of the co-ordinate system of this single
  balise group
  [EXTERNAL]
  , the
  ERTMS/ETCS on-board equipment
  [SELF]
  shall report its position by means of a position report based on two
  balise groups
  [EXTERNAL]
  reporting the train position in reference to the
  LRBG
  [EXTERNAL]
  and the “previous
  LRBG
  [EXTERNAL]
  ”,
  if
  [CONDITION]
  any.
- kind: ordinary

###### 3.4.2.3.3.1.1 (Requirement Type)
Note: Receiving this type of position report advises the RBC of the need to assign a co-ordinate system to this single balise group.
- WordTraceId: 14342
- atomic: false
- Legal Obligation: not applicable
- implement: false
- implementerEnhanced: Note: Receiving this type of position report advises the
  RBC
  [EXTERNAL]
  of the need to assign a co-ordinate system to this single
  balise group
  [EXTERNAL]
  .
- kind: Note

###### 3.4.2.3.3.2 (Requirement Type)
When a single balise group is detected and the previous LRBG is known, the position report based on two balise groups shall use as direction reference a move from the “previous LRBG” towards this single balise group (being the new LRBG): directional information in the position report pointing in the same direction as the direction reference shall be reported as “nominal”, otherwise as “reverse”.
- WordTraceId: 14475
- atomic: false
- Legal Obligation: mandatory
- implement: false
- implementerEnhanced: When
  [CONDITION]
  a single
  balise group
  [EXTERNAL]
  is detected and the
  previous
  LRBG
  [EXTERNAL]
  [LINKED_PHRASE]
  is known, the position report based on two
  balise groups
  [EXTERNAL]
  shall use as direction reference a move from the “
  previous
  LRBG
  [EXTERNAL]
  [LINKED_PHRASE]
  ” towards this single
  balise group
  [EXTERNAL]
  (being the new
  LRBG
  [EXTERNAL]
  ): directional information in the position report pointing in the same direction as the direction reference shall be reported as “nominal”, otherwise as “reverse”.
- kind: Definition
- KnownTermLink -> 3.4.2.3.3.1

###### 3.4.2.3.3.3 (Requirement Type)
If the “previous LRBG “ is not known, the “previous LRBG” and all directional information of the position report based on two balise groups shall be reported as “unknown”.
- WordTraceId: 14874
- atomic: true
- Legal Obligation: mandatory
- implement: false
- implementerEnhanced: If
  [CONDITION]
  the “
  previous
  LRBG
  [EXTERNAL]
  [LINKED_PHRASE]
  “ is not known, the “
  previous
  LRBG
  [EXTERNAL]
  [LINKED_PHRASE]
  ” and all directional information of the position report based on two
  balise groups
  [EXTERNAL]
  shall be reported as “unknown”.
- kind: Definition
- KnownTermLink -> 3.4.2.3.3.1

###### 3.4.2.3.3.4 (Requirement Type)
If a new single balise group (BG2), different from the current LRBG (BG1), becomes LRBG while the running direction of the train is opposite to the running direction when this current LRBG (BG1) was last passed, the “previous LRBG” and all directional information of the position report based on two balise groups shall be reported as “unknown” (see Figure 2a).
- WordTraceId: 15046
- atomic: true
- Legal Obligation: mandatory
- implement: false
- implementerEnhanced: If
  [CONDITION]
  a new single
  balise group
  [EXTERNAL]
  (BG2), different from the current
  LRBG
  [EXTERNAL]
  (BG1), becomes
  LRBG
  [EXTERNAL]
  while
  [TIME]
  the running direction of the train is opposite to the running direction
  when
  [CONDITION]
  this current
  LRBG
  [EXTERNAL]
  (BG1) was last passed, the “
  previous
  LRBG
  [EXTERNAL]
  [LINKED_PHRASE]
  ” and all directional information of the position report based on two
  balise groups
  [EXTERNAL]
  shall be reported as “unknown” (see Figure 2a).
- kind: Definition
- CrossRefLink -> 3.4.2.3.3.4[2].[f]2a.C
- KnownTermLink -> 3.4.2.3.3.1

###### 3.4.2.3.3.4[2] (Requirement Type)
- WordTraceId: 15408
- atomic: false
- Legal Obligation: not applicable
- implement: false
- kind: Placeholder

###### 3.4.2.3.3.4[2].[f]2a (Requirement Type)
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- WordTraceId: 15437
- atomic: false
- Legal Obligation: not applicable
- implement: false
- kind: Figure

###### 3.4.2.3.3.4[2].[f]2a.C (Requirement Type)
Figure 2a: Position report based on two balise groups versus train running direction
- WordTraceId: 15437
- atomic: true
- Legal Obligation: unknown
- implement: false
- implementerEnhanced: Figure 2a: Position report based on two
  balise groups
  [EXTERNAL]
  versus train running direction
- kind: Figure

###### 3.4.2.3.3.5 (Requirement Type)
If a single balise group, being the LRBG, is detected again, the LRBG and the “previous LRBG” of the position report based on two balise groups shall remain unchanged.
- WordTraceId: 15522
- atomic: true
- Legal Obligation: mandatory
- implement: true
- implementerEnhanced: If
  [CONDITION]
  a single
  balise group
  [EXTERNAL]
  , being the
  LRBG
  [EXTERNAL]
  , is detected
  again
  [LOOP]
  , the
  LRBG
  [EXTERNAL]
  and the “
  previous
  LRBG
  [EXTERNAL]
  [LINKED_PHRASE]
  ” of the position report based on two
  balise groups
  [EXTERNAL]
  shall remain unchanged.
- kind: ordinary
- KnownTermLink -> 3.4.2.3.3.1

###### 3.4.2.3.3.6 (Requirement Type)
The assignment of a co-ordinate system received from the RBC shall identify the balise group for which the assignment is given, and assign a balise group orientation “nominal” or “reverse” to this balise group
- WordTraceId: 15690
- atomic: true
- Legal Obligation: mandatory
- implement: true
- implementerEnhanced: The assignment of a co-ordinate system received from the
  RBC
  [EXTERNAL]
  shall identify the
  balise group
  [EXTERNAL]
  for which the assignment is given, and assign a
  balise group
  [EXTERNAL]
  orientation “nominal” or “reverse” to this
  balise group
  [EXTERNAL]
- kind: ordinary

###### 3.4.2.3.3.6.1 (Requirement Type)
Note: From the sequence of reported balise groups, the RBC can derive the balise group orientation with which the balise group was passed.
- WordTraceId: 15900
- atomic: false
- Legal Obligation: not applicable
- implement: false
- implementerEnhanced: Note: From the sequence of reported
  balise groups
  [EXTERNAL]
  , the
  RBC
  [EXTERNAL]
  can derive the
  balise group
  [EXTERNAL]
  orientation with which the
  balise group
  [EXTERNAL]
  was passed.
- kind: Note

###### 3.4.2.3.3.6.1[2] (Requirement Type)
- WordTraceId: 16040
- atomic: false
- Legal Obligation: not applicable
- implement: false
- kind: Placeholder

###### 3.4.2.3.3.6.1[2].[f]2b (Requirement Type)
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- WordTraceId: 16069
- atomic: false
- Legal Obligation: not applicable
- implement: false
- kind: Figure

###### 3.4.2.3.3.6.1[2].[f]2b.C (Requirement Type)
Figure 2b: Example for assigning a co-ordinate system
- WordTraceId: 16069
- atomic: true
- Legal Obligation: unknown
- implement: false
- kind: Figure

###### 3.4.2.3.3.7 (Requirement Type)
For single balise groups reported as LRBG and stored according to 3.6.2.2.2c, awaiting an assignment of a co-ordinate system, the ERTMS/ETCS on-board equipment shall be able to discriminate if a single balise has been reported more than once and with different “previous LRBGs” to the RBC.
- WordTraceId: 16123
- atomic: true
- Legal Obligation: mandatory
- implement: true
- implementerEnhanced: For
  single
  balise groups
  [EXTERNAL]
  [LINKED_PHRASE]
  reported as
  LRBG
  [EXTERNAL]
  and stored according to 3.6.2.2.2c, awaiting an assignment of a co-ordinate system, the
  ERTMS/ETCS on-board equipment
  [SELF]
  shall be able to discriminate
  if
  [CONDITION]
  a single
  balise
  [EXTERNAL]
  has been reported more than once and with different “
  previous
  LRBG
  [EXTERNAL]
  [LINKED_PHRASE]
  s
  [EXTERNAL]
  ” to the
  RBC
  [EXTERNAL]
  .
- kind: ordinary
- CrossRefLink -> 3.6.2.2.2.c
- KnownTermLink -> 3.4.2.3.1
- KnownTermLink -> 3.4.2.3.3.1

###### 3.4.2.3.3.7.1 (Requirement Type)
Note: For a single balise group reported as LRBG awaiting the assignment of a co-ordinate system also the rules for LRBGs reported to the RBC (see 3.6.2.2.2) apply.
- WordTraceId: 16413
- atomic: false
- Legal Obligation: not applicable
- implement: false
- implementerEnhanced: Note: For a single
  balise group
  [EXTERNAL]
  reported as
  LRBG
  [EXTERNAL]
  awaiting the assignment of a co-ordinate system also the rules for
  LRBGs
  [EXTERNAL]
  reported to the
  RBC
  [EXTERNAL]
  (see 3.6.2.2.2) apply.
- kind: Note
- CrossRefLink -> 3.6.2.2.2

###### 3.4.2.3.3.8 (Requirement Type)
A co-ordinate system assignment received from trackside shall be rejected by the ERTMS/ETCS on-board equipment if the referred LRBG is memorised (see 3.6.2.2.2c) to have been reported more than once and with different “previous LRBGs”.
- WordTraceId: 16578
- atomic: true
- Legal Obligation: mandatory
- implement: true
- implementerEnhanced: A co-ordinate system assignment received from
  trackside
  [EXTERNAL]
  shall be rejected by the
  ERTMS/ETCS on-board equipment
  [SELF]
  if
  [CONDITION]
  the referred
  LRBG
  [EXTERNAL]
  is memorised (see 3.6.2.2.2c) to have been reported more than once and with different “
  previous
  LRBG
  [EXTERNAL]
  [LINKED_PHRASE]
  s
  [EXTERNAL]
  ”.
- kind: ordinary
- CrossRefLink -> 3.6.2.2.2.c
- KnownTermLink -> 3.4.2.3.3.1

###### 3.4.2.3.3.8.1 (Requirement Type)
Note: If a single balise group is memorised, according to 3.6.2.2.2c, more than once, and with different “previous LRBGs”, the assignment of the co-ordinate system is ambiguous.
- WordTraceId: 16814
- atomic: false
- Legal Obligation: not applicable
- implement: false
- implementerEnhanced: Note:
  If
  [CONDITION]
  a single
  balise group
  [EXTERNAL]
  is memorised, according to 3.6.2.2.2c, more than once, and with different “
  previous
  LRBG
  [EXTERNAL]
  [LINKED_PHRASE]
  s
  [EXTERNAL]
  ”, the assignment of the co-ordinate system is ambiguous.
- kind: Note
- CrossRefLink -> 3.6.2.2.2.c
- KnownTermLink -> 3.4.2.3.3.1

##### 3.4.2.4 (Requirement Type)
Balise groups composed of one pair of duplicated balises
- WordTraceId: 16992
- atomic: false
- Legal Obligation: not applicable
- implement: false
- implementerEnhanced: Balise groups
  [EXTERNAL]
  composed of one pair of duplicated
  balises
  [EXTERNAL]
- kind: Heading

###### 3.4.2.4.1 (Requirement Type)
A group of two balises duplicating each other shall be treated as a single balise group in case where only one balise is correctly read.
- WordTraceId: 17049
- atomic: true
- Legal Obligation: mandatory
- implement: true
- implementerEnhanced: A group of two
  balises
  [EXTERNAL]
  duplicating each other shall be treated as a single
  balise group
  [EXTERNAL]
  in case
  [CONDITION]
  where only one
  balise
  [EXTERNAL]
  is correctly read.
- kind: ordinary

#### 3.4.3 (Requirement Type)
Balise Information Types and Usage
- WordTraceId: 17186
- atomic: false
- Legal Obligation: not applicable
- implement: false
- implementerEnhanced: Balise
  [EXTERNAL]
  Information Types and Usage
- kind: Heading

##### 3.4.3.1 (Requirement Type)
In level 1, all information to the on-board system is given from balise groups or additionally from EUROLOOPS or Radio Infill Units (see section 3.9). In level 2/3, balise groups are mostly used for location information.
- WordTraceId: 17221
- atomic: false
- Legal Obligation: unknown
- implement: true
- implementerEnhanced: In level 1, all information to the on-board system is given from
  balise groups
  [EXTERNAL]
  or additionally from
  EUROLOOPS
  [EXTERNAL]
  or Radio Infill Units (see section 3.9). In level 2/3,
  balise groups
  [EXTERNAL]
  are
  mostly
  [WEAK]
  used for location information.
- kind: ordinary
- CrossRefLink -> 3.9

##### 3.4.3.2 (Requirement Type)
A balise may contain directional information, i.e. valid either for nominal or for reverse direction, or may contain information valid for both directions. In level 1, this information can be of the following type (please refer to section 3.8.5):
- WordTraceId: 17471
- atomic: false
- Legal Obligation: optional
- implement: true
- implementerEnhanced: A
  balise
  [EXTERNAL]
  may contain directional information, i.e. valid either for nominal or for reverse direction, or may contain information valid for both directions. In level 1, this information can be of the following type (please refer to section 3.8.5):
- kind: ordinary
- CrossRefLink -> 3.8.5

###### 3.4.3.2.a (Requirement Type)
Non-infill
- WordTraceId: 17747
- atomic: true
- Legal Obligation: unknown
- implement: true
- ListNumberText: a)
- kind: ordinary

###### 3.4.3.2.b (Requirement Type)
Intentionally deleted
- WordTraceId: 17758
- atomic: false
- Legal Obligation: not applicable
- implement: false
- ListNumberText: b)
- kind: Placeholder

###### 3.4.3.2.c (Requirement Type)
Infill.
- WordTraceId: 17780
- atomic: true
- Legal Obligation: unknown
- implement: true
- ListNumberText: c)
- kind: ordinary

###### 3.4.3.2.1 (Requirement Type)
Intentionally deleted.
- WordTraceId: 17788
- atomic: false
- Legal Obligation: not applicable
- implement: false
- kind: Placeholder

###### 3.4.3.2.2 (Requirement Type)
Note: Infill information is referring to the location reference of an announced balise group.
- WordTraceId: 17811
- atomic: false
- Legal Obligation: not applicable
- implement: false
- implementerEnhanced: Note: Infill information is referring to the location reference of an announced
  balise group
  [EXTERNAL]
  .
- kind: Note

##### 3.4.3.3 (Requirement Type)
Some information shall be read also in sleeping mode and when no linking information is available (see Chapter 4 Use of received information). If such information is transmitted by balises, and if the information is directional, balise groups consisting of at least two balises shall be used.
- WordTraceId: 17905
- atomic: false
- Legal Obligation: mandatory
- implement: true
- implementerEnhanced: Some information
  [WEAK]
  shall be read also in sleeping mode and
  when
  [CONDITION]
  no linking information is available (see Chapter 4 Use of received information).
  If
  [CONDITION]
  such information is transmitted by
  balises
  [EXTERNAL]
  , and
  if
  [CONDITION]
  the information is directional,
  balise groups
  [EXTERNAL]
  consisting of
  at least
  [WEAK]
  two
  balises
  [EXTERNAL]
  shall be used.
- kind: ordinary

#### 3.4.4 (Requirement Type)
Linking
- WordTraceId: 18198
- atomic: false
- Legal Obligation: not applicable
- implement: false
- kind: Heading

##### 3.4.4.1 (Requirement Type)
Introduction
- WordTraceId: 18206
- atomic: false
- Legal Obligation: not applicable
- implement: false
- kind: Heading

###### 3.4.4.1.1 (Requirement Type)
Aim of linking:
- WordTraceId: 18219
- atomic: true
- Legal Obligation: unknown
- implement: false
- kind: Heading

###### 3.4.4.1.1.*[1] (Requirement Type)
To determine whether a balise group has been missed or not found within the expectation window (see section 3.4.4.4) and take the appropriate action.
- WordTraceId: 18236
- atomic: true
- Legal Obligation: unknown
- implement: true
- implementerEnhanced: To determine
  whether
  [CONDITION]
  a
  balise group
  [EXTERNAL]
  has been missed or not found within the expectation window (see section 3.4.4.4) and take the appropriate action.
- ListNumberText: ·
- kind: ordinary
- CrossRefLink -> 3.4.4.4

###### 3.4.4.1.1.*[2] (Requirement Type)
To assign a co-ordinate system to balise groups consisting of a single balise.
- WordTraceId: 18416
- atomic: true
- Legal Obligation: unknown
- implement: true
- implementerEnhanced: To assign a co-ordinate system to
  balise groups
  [EXTERNAL]
  consisting of a single
  balise
  [EXTERNAL]
  .
- ListNumberText: ·
- kind: ordinary

###### 3.4.4.1.1.*[3] (Requirement Type)
To correct the confidence interval due to odometer inaccuracy (see section 3.6.4).
- WordTraceId: 18495
- atomic: true
- Legal Obligation: unknown
- implement: true
- ListNumberText: ·
- kind: ordinary
- CrossRefLink -> 3.6.4

###### 3.4.4.1.2 (Requirement Type)
A balise group is linked when its linking information (see section 3.4.4.2) is known in advance.
- WordTraceId: 18607
- atomic: true
- Legal Obligation: unknown
- implement: true
- implementerEnhanced: A
  balise group
  [EXTERNAL]
  is linked
  when
  [CONDITION]
  its linking information (see section 3.4.4.2) is known in advance.
- kind: ordinary
- CrossRefLink -> 3.4.4.2

###### 3.4.4.1.2.1 (Requirement Type)
Note: In cases where a balise group contains repositioning information, the term linked also applies since the balise group is announced, marked as linked and contains repositioning information marked accordingly.
- WordTraceId: 18733
- atomic: false
- Legal Obligation: not applicable
- implement: false
- implementerEnhanced: Note: In cases where a
  balise group
  [EXTERNAL]
  contains repositioning information, the term linked also applies since the
  balise group
  [EXTERNAL]
  is announced, marked as linked and contains repositioning information marked accordingly.
- kind: Note

##### 3.4.4.2 (Requirement Type)
Content of linking information
- WordTraceId: 18947
- atomic: false
- Legal Obligation: not applicable
- implement: false
- kind: Heading

###### 3.4.4.2.1 (Requirement Type)
Linking information shall be composed of:
- WordTraceId: 18978
- atomic: true
- Legal Obligation: not applicable
- implement: false
- kind: Heading

###### 3.4.4.2.1.a (Requirement Type)
The identity of the linked balise group.
- WordTraceId: 19020
- atomic: true
- Legal Obligation: mandatory
- implement: true
- implementerEnhanced: The identity of the linked
  balise group
  [EXTERNAL]
  .
- ListNumberText: a)
- kind: ordinary

###### 3.4.4.2.1.b (Requirement Type)
Where the location reference of the group has to be found.
- WordTraceId: 19061
- atomic: true
- Legal Obligation: mandatory
- implement: true
- ListNumberText: b)
- kind: ordinary

###### 3.4.4.2.1.c (Requirement Type)
The accuracy of this location.
Note: If the reference balise is duplicated, it is the trackside responsibility to define the location accuracy to cover at least the location of the two duplicated balises.
- WordTraceId: 19120
- atomic: false
- Legal Obligation: mandatory
- implement: true
- implementerEnhanced: The accuracy of this location. Note:
  If
  [CONDITION]
  the reference
  balise
  [EXTERNAL]
  is duplicated, it is the
  trackside
  [EXTERNAL]
  responsibility to define the location accuracy to cover
  at least
  [WEAK]
  the location of the two duplicated
  balises
  [EXTERNAL]
  .
- ListNumberText: c)
- kind: ordinary

###### 3.4.4.2.1.d (Requirement Type)
The direction with which the linked balise group will be passed over (nominal or reverse).
- WordTraceId: 19325
- atomic: true
- Legal Obligation: mandatory
- implement: true
- implementerEnhanced: The
  direction with which the linked
  balise group
  [EXTERNAL]
  will be passed over
  [LINKED_PHRASE]
  (nominal or reverse).
- ListNumberText: d)
- kind: ordinary
- KnownTermLink -> 3.4.2.3.2.2

###### 3.4.4.2.1.e (Requirement Type)
The reaction required if a data consistency problem occurs with the expected balise group.
- WordTraceId: 19416
- atomic: true
- Legal Obligation: mandatory
- implement: true
- implementerEnhanced: The reaction required
  if
  [CONDITION]
  a data consistency problem occurs with the expected
  balise group
  [EXTERNAL]
  .
- ListNumberText: e)
- kind: ordinary

###### 3.4.4.2.1.1 (Requirement Type)
"Linking information is used" shall be interpreted as when balise group(s) are announced and the minimum safe antenna position has not yet passed the expectation window of the furthest announced balise group.
- WordTraceId: 19507
- atomic: true
- Legal Obligation: mandatory
- implement: false
- implementerEnhanced: "Linking information is used" shall be interpreted as
  when
  [CONDITION]
  balise group(s)
  [EXTERNAL]
  are announced and the minimum safe antenna position has
  not yet
  [TIME]
  passed the expectation window of the furthest announced
  balise group
  [EXTERNAL]
  .
- kind: Definition

###### 3.4.4.2.2 (Requirement Type)
Instead of the identity of a linked balise group it shall be possible to identify a following linked balise group as unknown but containing repositioning information
- WordTraceId: 19716
- atomic: true
- Legal Obligation: not applicable
- implement: false
- implementerEnhanced: Instead of the identity of a linked
  balise group
  [EXTERNAL]
  it shall be possible to identify a following linked
  balise group
  [EXTERNAL]
  as unknown but containing repositioning information
- kind: Heading

###### 3.4.4.2.2.1 (Requirement Type)
Intentionally deleted.
- WordTraceId: 19882
- atomic: false
- Legal Obligation: not applicable
- implement: false
- kind: Placeholder

###### 3.4.4.2.2.2 (Requirement Type)
Note 1: Regarding the repositioning information, see chapter 3.8.5.3.5 and 3.8.5.2.
- WordTraceId: 19905
- atomic: false
- Legal Obligation: mandatory
- implement: false
- kind: Note
- CrossRefLink -> 3.8.5.3.5
- CrossRefLink -> 3.8.5.2

###### 3.4.4.2.2.3 (Requirement Type)
Note 2: In case the identity of the next balise group is not unambiguously known because the route is not known by the trackside, this feature allows to link this balise group.
- WordTraceId: 20018
- atomic: false
- Legal Obligation: mandatory
- implement: false
- implementerEnhanced: Note 2:
  In case
  [CONDITION]
  the identity of the next
  balise group
  [EXTERNAL]
  is not unambiguously known because the route is not known by the
  trackside
  [EXTERNAL]
  , this feature allows to link this
  balise group
  [EXTERNAL]
  .
- kind: Note

###### 3.4.4.2.3 (Requirement Type)
For each linked balise group, the trackside shall select one of the following reactions to be used in case of data inconsistencies:
- WordTraceId: 20195
- atomic: true
- Legal Obligation: mandatory
- implement: true
- implementerEnhanced: For each
  [LOOP]
  linked
  balise group
  [EXTERNAL]
  , the
  trackside
  [EXTERNAL]
  shall select one of the following reactions to be used
  in case of
  [CONDITION]
  data inconsistencies:
- kind: ordinary

###### 3.4.4.2.3.a (Requirement Type)
Train trip (Trip mode, see Chapter 4)
- WordTraceId: 20327
- atomic: true
- Legal Obligation: mandatory (== 1)
- PlainText: Train trip  (Trip mode, see Chapter 4)
- implement: true
- ListNumberText: a)
- kind: ordinary

###### 3.4.4.2.3.b (Requirement Type)
Command service brake
- WordTraceId: 20366
- atomic: true
- Legal Obligation: mandatory (== 1)
- implement: true
- ListNumberText: b)
- kind: ordinary

###### 3.4.4.2.3.c (Requirement Type)
No reaction
- WordTraceId: 20389
- atomic: true
- Legal Obligation: mandatory (== 1)
- implement: true
- ListNumberText: c)
- kind: ordinary

###### 3.4.4.2.3[2] (Requirement Type)
For further details see section 3.16.2.
- WordTraceId: 20401
- atomic: true
- Legal Obligation: unknown
- implement: true
- kind: ordinary
- CrossRefLink -> 3.16.2

##### 3.4.4.3 (Requirement Type)
Unlinked Balise Groups
- WordTraceId: 20470
- atomic: false
- Legal Obligation: not applicable
- implement: false
- implementerEnhanced: Unlinked
  Balise Groups
  [EXTERNAL]
- kind: Heading

###### 3.4.4.3.1 (Requirement Type)
A balise group, which contains information that must be considered even when the balise group is not announced by linking, is called an unlinked balise group.
- WordTraceId: 20493
- atomic: true
- Legal Obligation: unknown
- implement: false
- implementerEnhanced: A
  balise group
  [EXTERNAL]
  , which contains information that must be considered
  even
  when
  [CONDITION]
  [WEAK]
  the
  balise group
  [EXTERNAL]
  is not announced by linking, is called an unlinked
  balise group
  [EXTERNAL]
  .
- kind: Definition

###### 3.4.4.3.2 (Requirement Type)
Unlinked balise groups shall consist at minimum of two balises.
- WordTraceId: 20653
- atomic: true
- Legal Obligation: mandatory
- implement: true
- implementerEnhanced: Unlinked
  balise groups
  [EXTERNAL]
  shall consist
  at minimum
  [WEAK]
  of two
  balises
  [EXTERNAL]
  .
- kind: ordinary

###### 3.4.4.3.3 (Requirement Type)
Unlinked balise groups shall always contain the unlinked balise group qualifier.
- WordTraceId: 20719
- atomic: true
- Legal Obligation: mandatory
- implement: true
- implementerEnhanced: Unlinked
  balise groups
  [EXTERNAL]
  shall always contain the unlinked
  balise group
  [EXTERNAL]
  qualifier.
- kind: ordinary

##### 3.4.4.4 (Requirement Type)
Rules related to linking
- WordTraceId: 20800
- atomic: false
- Legal Obligation: not applicable
- implement: false
- kind: Heading

###### 3.4.4.4.1 (Requirement Type)
When no linking information is used on-board, all balise groups shall be taken into account.
- WordTraceId: 20825
- atomic: true
- Legal Obligation: mandatory
- implement: true
- implementerEnhanced: When
  [CONDITION]
  no
  linking information is used
  [LINKED_PHRASE]
  on-board, all
  balise groups
  [EXTERNAL]
  shall be taken into account.
- kind: ordinary
- KnownTermLink -> 3.4.4.2.1.1

###### 3.4.4.4.2 (Requirement Type)
When linking information is used on-board, only balise groups marked as linked and included in the linking information and balise groups marked as unlinked shall be taken into account.
- WordTraceId: 20918
- atomic: true
- Legal Obligation: mandatory
- implement: true
- implementerEnhanced: When
  [CONDITION]
  linking information is used
  [LINKED_PHRASE]
  on-board, only
  balise groups
  [EXTERNAL]
  marked as linked and included in the linking information and
  balise groups
  [EXTERNAL]
  marked as unlinked shall be taken into account.
- kind: ordinary
- KnownTermLink -> 3.4.4.2.1.1

###### 3.4.4.4.2.1 (Requirement Type)
When linking information is used on-board and the expected balise group is referred in the linking information with a balise group with ID “unknown”, a balise group marked as linked shall only be taken into account if:
- WordTraceId: 21103
- atomic: true
- Legal Obligation: mandatory
- implement: true
- implementerEnhanced: When
  [CONDITION]
  linking information is used
  [LINKED_PHRASE]
  on-board and the expected
  balise group
  [EXTERNAL]
  is referred in the linking information with a
  balise group
  [EXTERNAL]
  with ID “unknown”, a
  balise group
  [EXTERNAL]
  marked as linked shall only be taken into account
  if
  [CONDITION]
  :
- kind: ordinary
- KnownTermLink -> 3.4.4.2.1.1

###### 3.4.4.4.2.1.a (Requirement Type)
the on-board equipment can determine the orientation of the linked balise group by information from the balise group itself (therefore excluding for example single balise groups), AND
- WordTraceId: 21322
- atomic: true
- Legal Obligation: mandatory
- implement: true
- implementerEnhanced: the
  on-board equipment
  [SELF]
  can determine the orientation of the linked
  balise group
  [EXTERNAL]
  by information from the
  balise group
  [EXTERNAL]
  itself (therefore excluding
  for example
  [WEAK]
  single
  balise groups
  [EXTERNAL]
  [LINKED_PHRASE]
  ), AND
- ListNumberText: a)
- kind: ordinary
- KnownTermLink -> 3.4.2.3.1

###### 3.4.4.4.2.1.b (Requirement Type)
the balise group contains repositioning information valid for the train orientation, AND
- WordTraceId: 21506
- atomic: true
- Legal Obligation: mandatory
- implement: true
- implementerEnhanced: the
  balise group
  [EXTERNAL]
  contains repositioning information valid for the train orientation, AND
- ListNumberText: b)
- kind: ordinary

###### 3.4.4.4.2.1.c (Requirement Type)
the balise group is crossed with the direction announced in the linking information.
- WordTraceId: 21595
- atomic: true
- Legal Obligation: mandatory
- implement: true
- implementerEnhanced: the
  balise group
  [EXTERNAL]
  is crossed with the direction announced in the linking information.
- ListNumberText: c)
- kind: ordinary

###### 3.4.4.4.3 (Requirement Type)
The on-board equipment shall accept a balise group marked as linked and included in the linking information (i.e. the balise giving the location reference) from
- WordTraceId: 21680
- atomic: true
- Legal Obligation: mandatory
- implement: true
- implementerEnhanced: The
  on-board equipment
  [SELF]
  shall accept a
  balise group
  [EXTERNAL]
  marked as linked and included in the linking information (i.e. the
  balise
  [EXTERNAL]
  giving the location reference) from
- kind: ordinary

###### 3.4.4.4.3.*[1] (Requirement Type)
when the max safe front end of the train has passed the first possible location of the balise group
- WordTraceId: 21842
- atomic: true
- Legal Obligation: unknown
- implement: true
- implementerEnhanced: when
  [CONDITION]
  the max safe front end of the train has passed the first possible location of the
  balise group
  [EXTERNAL]
- ListNumberText: ·
- kind: ordinary

###### 3.4.4.4.3[2] (Requirement Type)
until
- WordTraceId: 21943
- atomic: true
- Legal Obligation: unknown
- implement: true
- implementerEnhanced: until
  [TIME]
- kind: ordinary

###### 3.4.4.4.3[2].*[1] (Requirement Type)
the min safe front end of the train has passed the last possible location of the balise group
- WordTraceId: 21950
- atomic: true
- Legal Obligation: unknown
- implement: true
- implementerEnhanced: the min safe front end of the train has passed the last possible location of the
  balise group
  [EXTERNAL]
- ListNumberText: ·
- kind: ordinary

###### 3.4.4.4.3[3] (Requirement Type)
taking the offset between the front of the train and the balise antenna into account.
- WordTraceId: 22044
- atomic: true
- Legal Obligation: unknown
- implement: true
- kind: ordinary

###### 3.4.4.4.3[3].1 (Requirement Type)
Note: The first possible location and the last possible location of the balise group are defined by the linking distance and the location accuracy.
- WordTraceId: 22130
- atomic: false
- Legal Obligation: not applicable
- implement: false
- implementerEnhanced: Note: The first possible location and the last possible location of the
  balise group
  [EXTERNAL]
  are defined by the linking distance and the location accuracy.
- ListNumberText: 3.4.4.4.3.1
- kind: Note

###### 3.4.4.4.3[3].2 (Requirement Type)
Note: The interval between the outer limits to accept the balise group defines the expectation window.
- WordTraceId: 22278
- atomic: false
- Legal Obligation: not applicable
- implement: false
- implementerEnhanced: Note: The interval between the outer limits to accept the
  balise group
  [EXTERNAL]
  defines the expectation window.
- ListNumberText: 3.4.4.4.3.2
- kind: Note

###### 3.4.4.4.4 (Requirement Type)
In case of a balise group containing repositioning information, the first possible location shall start from the previously linked balise group.
- WordTraceId: 22381
- atomic: true
- Legal Obligation: mandatory
- implement: true
- implementerEnhanced: In case of
  [CONDITION]
  a
  balise group
  [EXTERNAL]
  containing repositioning information, the first possible location shall start from the previously linked
  balise group
  [EXTERNAL]
  .
- kind: ordinary

###### 3.4.4.4.5 (Requirement Type)
The on-board equipment shall expect balise groups one by one (i.e., it shall supervise only one expectation window at a time) according to the order given by linking information.
- WordTraceId: 22526
- atomic: false
- Legal Obligation: mandatory
- implement: true
- implementerEnhanced: The
  on-board equipment
  [SELF]
  shall expect
  balise groups
  [EXTERNAL]
  one by one (i.e., it shall supervise only one expectation window at a
  time
  [TIME]
  ) according to the order given by linking information.
- kind: ordinary

###### 3.4.4.4.6 (Requirement Type)
The ERTMS/ETCS on-board equipment shall stop expecting a balise group and shall expect the next one announced in the linking information (if any) when:
- WordTraceId: 22705
- atomic: false
- Legal Obligation: mandatory
- implement: true
- implementerEnhanced: The
  ERTMS/ETCS on-board equipment
  [SELF]
  shall stop expecting a
  balise group
  [EXTERNAL]
  and shall expect the next one announced in the linking information (
  if
  [CONDITION]
  any)
  when
  [CONDITION]
  :
- kind: ordinary

###### 3.4.4.4.6.a (Requirement Type)
the balise group is found inside its expectation window
- WordTraceId: 22857
- atomic: true
- Legal Obligation: unknown
- implement: true
- implementerEnhanced: the
  balise group
  [EXTERNAL]
  is found inside its expectation window
- ListNumberText: a)
- kind: ordinary

###### 3.4.4.4.6.b (Requirement Type)
a linking consistency error is found, see 3.16.2.3.1
- WordTraceId: 22913
- atomic: true
- Legal Obligation: unknown
- implement: true
- ListNumberText: b)
- kind: ordinary
- CrossRefLink -> 3.16.2.3.1

###### 3.4.4.4.6.1 (Requirement Type)
Linking consistency error due to early reception of balise group expected later (see 3.16.2.3.1 c)): if the balise group found is the next one announced in the linking information, the ERTMS/ETCS on-board equipment shall check its linking consistency and apply again clause 3.4.4.4.6, i.e. it will immediately expect the further next balise group announced in the linking information.
- WordTraceId: 22966
- atomic: true
- Legal Obligation: mandatory
- implement: true
- implementerEnhanced: Linking consistency error due to early reception of
  balise group
  [EXTERNAL]
  expected later (see 3.16.2.3.1 c)):
  if
  [CONDITION]
  the
  balise group
  [EXTERNAL]
  found is the next one announced in the linking information, the
  ERTMS/ETCS on-board equipment
  [SELF]
  shall check its linking consistency and apply
  again
  [LOOP]
  clause 3.4.4.4.6, i.e. it will
  immediately
  [WEAK]
  expect the further next
  balise group
  [EXTERNAL]
  announced in the linking information.
- kind: ordinary
- CrossRefLink -> 3.16.2.3.1.c
- CrossRefLink -> 3.4.4.4.6

### 3.5 (Requirement Type)
Management of Radio Communication
- WordTraceId: 23351
- atomic: false
- Legal Obligation: not applicable
- implement: false
- kind: Heading

#### 3.5.1 (Requirement Type)
PLACEHOLDER REQUIREMENT - DO NOT TRACE
- WordTraceId: 23385
- atomic: false
- Legal Obligation: not applicable
- implement: false
- kind: Placeholder

##### 3.5.1.1 (Requirement Type)
Note: the following section refers to the behaviour of the user application interacting with Euroradio protocols. How the messages are actually transported from the sender to the receiver user application is not relevant for this description.
- WordTraceId: 23385
- atomic: false
- Legal Obligation: not applicable
- implement: false
- kind: Note

#### 3.5.2 (Requirement Type)
General
- WordTraceId: 23628
- atomic: false
- Legal Obligation: not applicable
- implement: false
- kind: Heading

##### 3.5.2.1 (Requirement Type)
Each communication session managed by an entity shall allow the exchange of data with only one other entity.
- WordTraceId: 23636
- atomic: true
- Legal Obligation: mandatory
- implement: true
- kind: ordinary

##### 3.5.2.2 (Requirement Type)
Note: in the following sections reference is made to safe radio connections, whose definition and management is contained in Euroradio specification.
- WordTraceId: 23745
- atomic: false
- Legal Obligation: not applicable
- implement: false
- kind: Note

##### 3.5.2.3 (Requirement Type)
The information Initiation of a Communication Session and Version not Compatible (see sections 3.5.3 and 3.17) shall be the same in every system version.
- WordTraceId: 23895
- atomic: true
- Legal Obligation: mandatory
- implement: true
- kind: ordinary
- CrossRefLink -> 3.5.3
- CrossRefLink -> 3.17

#### 3.5.3 (Requirement Type)
Establishing a communication session
- WordTraceId: 24107
- atomic: false
- Legal Obligation: not applicable
- implement: false
- kind: Heading

##### 3.5.3.1 (Requirement Type)
It shall be possible for ERTMS/ETCS on-board equipment and RBC to initiate a communication session.
- WordTraceId: 24144
- atomic: true
- Legal Obligation: mandatory
- implement: true
- implementerEnhanced: It shall be possible for
  ERTMS/ETCS on-board equipment
  [SELF]
  and
  RBC
  [EXTERNAL]
  to initiate a communication session.
- kind: ordinary

##### 3.5.3.2 (Requirement Type)
A Radio Infill Unit (see section 3.9.3) shall never initiate a communication session.
- WordTraceId: 24244
- atomic: true
- Legal Obligation: mandatory
- implement: true
- implementerEnhanced: A
  Radio Infill Unit
  [EXTERNAL]
  (see section 3.9.3) shall never initiate a communication session.
- kind: ordinary
- CrossRefLink -> 3.9.3

##### 3.5.3.3 (Requirement Type)
Note: Only communication sessions between an ERTMS/ETCS on-board equipment and a trackside equipment (RBC or Radio Infill Unit) are considered here.
- WordTraceId: 24359
- atomic: false
- Legal Obligation: not applicable
- implement: false
- implementerEnhanced: Note: Only communication sessions between an
  ERTMS/ETCS on-board equipment
  [SELF]
  and a
  trackside
  [EXTERNAL]
  equipment (
  RBC
  [EXTERNAL]
  or
  Radio Infill Unit
  [EXTERNAL]
  ) are considered here.
- kind: Note

##### 3.5.3.4 (Requirement Type)
The on-board shall establish a communication session
- WordTraceId: 24508
- atomic: true
- Legal Obligation: mandatory
- implement: true
- kind: ordinary

###### 3.5.3.4.a (Requirement Type)
At Start of Mission (only if level 2 or 3).
- WordTraceId: 24561
- atomic: true
- Legal Obligation: unknown
- implement: true
- implementerEnhanced: At Start of Mission (only
  if
  [CONDITION]
  level 2 or 3).
- ListNumberText: a)
- kind: ordinary

###### 3.5.3.4.b (Requirement Type)
If ordered from trackside.
- WordTraceId: 24605
- atomic: true
- Legal Obligation: unknown
- implement: true
- implementerEnhanced: If
  [CONDITION]
  ordered from
  trackside
  [EXTERNAL]
  .
- ListNumberText: b)
- kind: ordinary

###### 3.5.3.4.c (Requirement Type)
If a mode change, not considered as an End of Mission, has to be reported to the RBC (only if level 2 or 3)
- WordTraceId: 24632
- atomic: true
- Legal Obligation: unknown
- implement: true
- implementerEnhanced: If
  [CONDITION]
  a mode change, not considered as an End of Mission, has to be reported to the
  RBC
  [EXTERNAL]
  (only
  if
  [CONDITION]
  level 2 or 3)
- ListNumberText: c)
- kind: ordinary

###### 3.5.3.4.d (Requirement Type)
If the driver has manually changed the level to 2 or 3
- WordTraceId: 24740
- atomic: true
- Legal Obligation: unknown
- implement: true
- implementerEnhanced: If
  [CONDITION]
  the
  driver
  [EXTERNAL]
  has manually changed the level to 2 or 3
- ListNumberText: d)
- kind: ordinary

###### 3.5.3.4.e (Requirement Type)
When the train front reaches the end of an announced radio hole
- WordTraceId: 24795
- atomic: true
- Legal Obligation: unknown
- implement: true
- implementerEnhanced: When
  [CONDITION]
  the train front reaches the end of an announced radio hole
- ListNumberText: e)
- kind: ordinary

###### 3.5.3.4.f (Requirement Type)
When the previous communication session is considered as terminated due to loss of safe radio connection (refer to 3.5.4.2.1)
- WordTraceId: 24859
- atomic: true
- Legal Obligation: unknown
- implement: true
- implementerEnhanced: When
  [CONDITION]
  the previous communication session is considered as terminated due to loss of safe radio connection (refer to 3.5.4.2.1)
- ListNumberText: f)
- kind: ordinary
- CrossRefLink -> 3.5.4.2.1

###### 3.5.3.4.g (Requirement Type)
When a Start of Mission procedure, during which no communication session could be established, is completed in level 2 or 3
- WordTraceId: 24985
- atomic: true
- Legal Obligation: unknown
- implement: true
- implementerEnhanced: When
  [CONDITION]
  a Start of Mission procedure,
  during
  [TIME]
  which no communication session could be established, is completed in level 2 or 3
- ListNumberText: g)
- kind: ordinary

###### 3.5.3.4.1 (Requirement Type)
In respect of a), b), c), d) and e) of 3.5.3.4, the on-board shall not establish a new communication session with an RBC/RIU in case a communication session is currently being established or is already established with this RBC/RIU.
- WordTraceId: 25109
- atomic: true
- Legal Obligation: mandatory
- implement: true
- implementerEnhanced: In respect of a), b), c), d) and e) of 3.5.3.4, the on-board shall not establish a new communication session with an
  RBC
  [EXTERNAL]
  /
  RIU
  [EXTERNAL]
  in case
  [CONDITION]
  a communication session is currently being established or is already established with this
  RBC
  [EXTERNAL]
  /
  RIU
  [EXTERNAL]
  .
- kind: ordinary
- CrossRefLink -> 3.5.3.4.a
- CrossRefLink -> 3.5.3.4.b
- CrossRefLink -> 3.5.3.4.c
- CrossRefLink -> 3.5.3.4.d
- CrossRefLink -> 3.5.3.4.e

##### 3.5.3.5 (Requirement Type)
The order to contact an RBC shall include
- WordTraceId: 25342
- atomic: true
- Legal Obligation: mandatory
- implement: true
- implementerEnhanced: The order to contact an
  RBC
  [EXTERNAL]
  shall include
- kind: ordinary

###### 3.5.3.5.a (Requirement Type)
The identity of the RBC.
- WordTraceId: 25384
- atomic: true
- Legal Obligation: unknown
- implement: true
- implementerEnhanced: The identity of the
  RBC
  [EXTERNAL]
  .
- ListNumberText: a)
- kind: ordinary

###### 3.5.3.5.b (Requirement Type)
The telephone number of the RBC.
- WordTraceId: 25409
- atomic: true
- Legal Obligation: unknown
- implement: true
- implementerEnhanced: The telephone number of the
  RBC
  [EXTERNAL]
  .
- ListNumberText: b)
- kind: ordinary

###### 3.5.3.5.c (Requirement Type)
The action to be performed (establish/terminate the session).
- WordTraceId: 25442
- atomic: true
- Legal Obligation: unknown
- implement: true
- ListNumberText: c)
- kind: ordinary

###### 3.5.3.5.d (Requirement Type)
Whether this applies also to Sleeping units.
- WordTraceId: 25504
- atomic: true
- Legal Obligation: unknown
- implement: true
- implementerEnhanced: Whether
  [CONDITION]
  this applies also to Sleeping units.
- ListNumberText: d)
- kind: ordinary

###### 3.5.3.5.1 (Requirement Type)
See table at the end of section 3.5.3.
- WordTraceId: 25549
- atomic: true
- Legal Obligation: unknown
- implement: true
- kind: ordinary
- CrossRefLink -> 3.5.3

###### 3.5.3.5.2 (Requirement Type)
If the ERTMS/ETCS on-board equipment has to establish a communication session with an RBC whilst in session with another RBC, the existing communication session shall be terminated (see 3.5.5.2 for details) and the new one shall be established. Exception: the order to contact an Accepting RBC shall not terminate the communication session with the Handing Over RBC.
- WordTraceId: 25589
- atomic: false
- Legal Obligation: mandatory
- implement: true
- implementerEnhanced: If
  [CONDITION]
  the
  ERTMS/ETCS on-board equipment
  [SELF]
  has to establish a communication session with an
  RBC
  [EXTERNAL]
  whilst in session with another
  RBC
  [EXTERNAL]
  , the existing communication session shall be terminated (see 3.5.5.2 for details) and the new one shall be established. Exception: the order to contact an Accepting
  RBC
  [EXTERNAL]
  shall not terminate the communication session with the Handing Over
  RBC
  [EXTERNAL]
  .
- kind: ordinary
- CrossRefLink -> 3.5.5.2

###### 3.5.3.5.3 (Requirement Type)
The order to contact an Accepting RBC shall be part of the RBC transition order and shall include:
- WordTraceId: 25956
- atomic: false
- Legal Obligation: mandatory
- implement: true
- implementerEnhanced: The order to contact an Accepting
  RBC
  [EXTERNAL]
  shall be part of the
  RBC
  [EXTERNAL]
  transition order and shall include:
- kind: ordinary

###### 3.5.3.5.3.a (Requirement Type)
The identity of the Accepting RBC.
- WordTraceId: 26055
- atomic: true
- Legal Obligation: unknown
- implement: true
- implementerEnhanced: The identity of the Accepting
  RBC
  [EXTERNAL]
  .
- ListNumberText: a)
- kind: ordinary

###### 3.5.3.5.3.b (Requirement Type)
The telephone number of the Accepting RBC.
- WordTraceId: 26090
- atomic: true
- Legal Obligation: unknown
- implement: true
- implementerEnhanced: The telephone number of the Accepting
  RBC
  [EXTERNAL]
  .
- ListNumberText: b)
- kind: ordinary

###### 3.5.3.5.3.c (Requirement Type)
Whether this applies also to Sleeping unit.
- WordTraceId: 26133
- atomic: true
- Legal Obligation: unknown
- implement: true
- implementerEnhanced: Whether
  [CONDITION]
  this applies also to Sleeping unit.
- ListNumberText: c)
- kind: ordinary

##### 3.5.3.6 (Requirement Type)
The order to contact a Radio Infill Unit shall include
- WordTraceId: 26177
- atomic: true
- Legal Obligation: mandatory
- implement: true
- implementerEnhanced: The order to contact a
  Radio Infill Unit
  [EXTERNAL]
  shall include
- kind: ordinary

###### 3.5.3.6.a (Requirement Type)
The identity of the Radio Infill Unit
- WordTraceId: 26232
- atomic: true
- Legal Obligation: unknown
- implement: true
- implementerEnhanced: The identity of the
  Radio Infill Unit
  [EXTERNAL]
- ListNumberText: a)
- kind: ordinary

###### 3.5.3.6.b (Requirement Type)
The telephone number of the Radio Infill Unit
- WordTraceId: 26270
- atomic: true
- Legal Obligation: unknown
- implement: true
- implementerEnhanced: The telephone number of the
  Radio Infill Unit
  [EXTERNAL]
- ListNumberText: b)
- kind: ordinary

###### 3.5.3.6.c (Requirement Type)
The action to be performed (establish/terminate the session).
- WordTraceId: 26316
- atomic: true
- Legal Obligation: unknown
- implement: true
- ListNumberText: c)
- kind: ordinary

##### 3.5.3.7 (Requirement Type)
If the establishment of a communication session is initiated by the on-board, it shall be performed according to the following steps:
- WordTraceId: 26378
- atomic: true
- Legal Obligation: not applicable
- implement: false
- implementerEnhanced: If
  [CONDITION]
  the establishment of a communication session is initiated by the on-board, it shall be performed according to the following steps:
- kind: Heading

###### 3.5.3.7.a (Requirement Type)
The on-board shall request the set-up of a safe radio connection with the trackside. If this request is part of an on-going Start of Mission procedure, it shall be repeated until successful or a defined number of times (see Appendix A3.1).
- WordTraceId: 26513
- atomic: false
- Legal Obligation: mandatory
- implement: true
- implementerEnhanced: The on-board shall request the set-up of a safe radio connection with the
  trackside
  [EXTERNAL]
  .
  If
  [CONDITION]
  this request is part of an on-going Start of Mission procedure, it shall be
  repeated
  [LOOP]
  until
  [TIME]
  successful or a defined number of times (see Appendix A3.1).
- ListNumberText: a)
- kind: ordinary
- CrossRefLink -> A.3.1

###### 3.5.3.7.a[2] (Requirement Type)
If this request is not part of an on-going Start of Mission procedure, it shall be repeated until at least one of the following conditions is met:
- WordTraceId: 26753
- atomic: true
- Legal Obligation: mandatory
- implement: true
- implementerEnhanced: If
  [CONDITION]
  this request is not part of an on-going Start of Mission procedure, it shall be
  repeated
  [LOOP]
  until
  [TIME]
  at least
  [WEAK]
  one of the following conditions is met:
- kind: ordinary

###### 3.5.3.7.a[2].*[1] (Requirement Type)
Safe radio connection is set up
- WordTraceId: 26900
- atomic: true
- Legal Obligation: mandatory (>= 1)
- implement: true
- ListNumberText: ·
- kind: ordinary

###### 3.5.3.7.a[2].*[2] (Requirement Type)
End of Mission is performed
- WordTraceId: 26932
- atomic: true
- Legal Obligation: mandatory (>= 1)
- implement: true
- ListNumberText: ·
- kind: ordinary

###### 3.5.3.7.a[2].*[3] (Requirement Type)
Order to terminate communication session is received from trackside
- WordTraceId: 26960
- atomic: true
- Legal Obligation: mandatory (>= 1)
- implement: true
- implementerEnhanced: Order to terminate communication session is received from
  trackside
  [EXTERNAL]
- ListNumberText: ·
- kind: ordinary

###### 3.5.3.7.a[2].*[4] (Requirement Type)
The train passes a level transition border (from level 2/3 to level 0, NTC, 1) with its front end.
- WordTraceId: 27028
- atomic: true
- Legal Obligation: mandatory (>= 1)
- implement: true
- ListNumberText: ·
- kind: ordinary

###### 3.5.3.7.a[2].*[5] (Requirement Type)
Order to establish communication session with a different RBC is received from trackside and the order does not request to contact an Accepting RBC.
- WordTraceId: 27127
- atomic: true
- Legal Obligation: mandatory (>= 1)
- implement: true
- implementerEnhanced: Order to establish communication session with a different
  RBC
  [EXTERNAL]
  is received from
  trackside
  [EXTERNAL]
  and the order does not request to contact an Accepting
  RBC
  [EXTERNAL]
  .
- ListNumberText: ·
- kind: ordinary

###### 3.5.3.7.a[2].*[6] (Requirement Type)
The train passes a RBC/RBC border with its front end.
- WordTraceId: 27276
- atomic: true
- Legal Obligation: mandatory (>= 1)
- implement: true
- implementerEnhanced: The train passes a
  RBC
  [EXTERNAL]
  /
  RBC
  [EXTERNAL]
  border with its front end.
- ListNumberText: ·
- kind: ordinary

###### 3.5.3.7.a[2].*[7] (Requirement Type)
The train front passes the start of an announced radio hole
- WordTraceId: 27330
- atomic: true
- Legal Obligation: mandatory (>= 1)
- implement: true
- ListNumberText: ·
- kind: ordinary

###### 3.5.3.7.a[2].*[8] (Requirement Type)
Regards RIUs only: Level 1 is left
- WordTraceId: 27390
- atomic: true
- Legal Obligation: mandatory (>= 1)
- implement: true
- ListNumberText: ·
- kind: ordinary

###### 3.5.3.7.a[3] (Requirement Type)
A request shall be repeated immediately after EURORADIO has indicated that setting up the safe radio connection has failed.
- WordTraceId: 27425
- atomic: true
- Legal Obligation: mandatory
- implement: true
- implementerEnhanced: A request shall be
  repeated
  [LOOP]
  immediately
  [WEAK]
  after
  [TIME]
  EURORADIO has indicated that setting up the safe radio connection has failed.
- kind: ordinary

###### 3.5.3.7.b (Requirement Type)
As soon as the safe radio connection is set-up, the on-board shall send the message Initiation of communication session to the trackside.
- WordTraceId: 27549
- atomic: true
- Legal Obligation: mandatory
- implement: true
- implementerEnhanced: As soon as
  [WEAK]
  the safe radio connection is set-up, the on-board shall send the message Initiation of communication session to the
  trackside
  [EXTERNAL]
  .
- ListNumberText: b)
- kind: ordinary

###### 3.5.3.7.c (Requirement Type)
As soon as the trackside receives the information, it shall send the system version.
- WordTraceId: 27688
- atomic: true
- Legal Obligation: mandatory
- implement: true
- implementerEnhanced: As soon as
  [WEAK]
  the
  trackside
  [EXTERNAL]
  receives the information, it shall send the system version.
- ListNumberText: c)
- kind: ordinary

##### 3.5.3.8 (Requirement Type)
When the on-board receives the system version it shall consider the communication session established and:
- WordTraceId: 27774
- atomic: true
- Legal Obligation: mandatory
- implement: true
- implementerEnhanced: When
  [CONDITION]
  the on-board receives the system version it shall consider the communication session established and:
- kind: ordinary

###### 3.5.3.8.a (Requirement Type)
If one of its supported system versions is compatible with the one sent by trackside, it shall send a session established report, including its telephone numbers, to the trackside.
- WordTraceId: 27881
- atomic: true
- Legal Obligation: mandatory
- implement: true
- implementerEnhanced: If
  [CONDITION]
  one of its supported system versions is compatible with the one sent by
  trackside
  [EXTERNAL]
  , it shall send a session established report, including its telephone numbers, to the
  trackside
  [EXTERNAL]
  .
- ListNumberText: a)
- kind: ordinary

###### 3.5.3.8.b (Requirement Type)
If none of its supported system versions is compatible with the one sent by trackside, it shall send a version independent message indicating “No compatible version supported”. It shall inform the driver and shall terminate the communication session.
- WordTraceId: 28062
- atomic: false
- Legal Obligation: mandatory
- implement: true
- implementerEnhanced: If
  [CONDITION]
  none of its supported system versions is compatible with the one sent by
  trackside
  [EXTERNAL]
  , it shall send a version independent message indicating “No compatible version supported”. It shall inform the
  driver
  [EXTERNAL]
  and shall terminate the communication session.
- ListNumberText: b)
- kind: ordinary

##### 3.5.3.9 (Requirement Type)
When the trackside receives the session established report or the information that no compatible system version is supported by the on-board, it shall consider the communication session established.
- WordTraceId: 28313
- atomic: true
- Legal Obligation: mandatory
- implement: true
- implementerEnhanced: When
  [CONDITION]
  the
  trackside
  [EXTERNAL]
  receives the session established report or the information that no compatible system version is supported by the on-board, it shall consider the communication session established.
- kind: ordinary

###### 3.5.3.9.1 (Requirement Type)
Intentionally deleted.
- WordTraceId: 28512
- atomic: false
- Legal Obligation: not applicable
- implement: false
- kind: Placeholder

###### 3.5.3.9.1[2] (Requirement Type)
- WordTraceId: 28535
- atomic: false
- Legal Obligation: not applicable
- implement: false
- kind: Placeholder

###### 3.5.3.9.1[2].[f]3 (Requirement Type)
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- WordTraceId: 28553
- atomic: false
- Legal Obligation: not applicable
- implement: false
- kind: Figure

###### 3.5.3.9.1[2].[f]3.C (Requirement Type)
Figure {Figure 3}: Establishment initiated by on-board
- WordTraceId: 28553
- atomic: true
- Legal Obligation: unknown
- PlainText: Figure 3: Establishment initiated by on-board
- implement: false
- kind: Figure

##### 3.5.3.10 (Requirement Type)
If the establishment of a communication session is initiated by the RBC, it shall be performed according to the following steps:
- WordTraceId: 28624
- atomic: true
- Legal Obligation: not applicable
- implement: false
- implementerEnhanced: If
  [CONDITION]
  the establishment of a communication session is initiated by the
  RBC
  [EXTERNAL]
  , it shall be performed according to the following steps:
- kind: Heading

###### 3.5.3.10.a (Requirement Type)
The trackside shall request the set-up of a safe radio connection with the on-board.
- WordTraceId: 28754
- atomic: true
- Legal Obligation: mandatory
- implement: true
- implementerEnhanced: The
  trackside
  [EXTERNAL]
  shall request the set-up of a safe radio connection with the on-board.
- ListNumberText: a)
- kind: ordinary

###### 3.5.3.10.b (Requirement Type)
As soon as the safe radio connection is set-up, the trackside shall send the message Initiation of communication session to the on-board.
- WordTraceId: 28839
- atomic: true
- Legal Obligation: mandatory
- implement: true
- implementerEnhanced: As soon as
  [WEAK]
  the safe radio connection is set-up, the
  trackside
  [EXTERNAL]
  shall send the message Initiation of communication session to the on-board.
- ListNumberText: b)
- kind: ordinary

###### 3.5.3.10.c (Requirement Type)
When the on-board receives the information, it shall consider the communication session established and send a session established report to the trackside.
- WordTraceId: 28978
- atomic: true
- Legal Obligation: mandatory
- implement: true
- implementerEnhanced: When
  [CONDITION]
  the on-board receives the information, it shall consider the communication session established and send a session established report to the
  trackside
  [EXTERNAL]
  .
- ListNumberText: c)
- kind: ordinary

###### 3.5.3.10.d (Requirement Type)
When the trackside receives the session established report, it shall consider the communication session established.
- WordTraceId: 29134
- atomic: true
- Legal Obligation: mandatory
- implement: true
- implementerEnhanced: When
  [CONDITION]
  the
  trackside
  [EXTERNAL]
  receives the session established report, it shall consider the communication session established.
- ListNumberText: d)
- kind: ordinary

###### 3.5.3.10.d[2] (Requirement Type)
- WordTraceId: 29253
- atomic: false
- Legal Obligation: not applicable
- implement: false
- kind: Placeholder

###### 3.5.3.10.d[2].[f]4 (Requirement Type)
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- WordTraceId: 29271
- atomic: false
- Legal Obligation: mandatory
- implement: false
- kind: Figure

###### 3.5.3.10.d[2].[f]4.C (Requirement Type)
Figure {Figure 4}: Establishment initiated by the RBC
- WordTraceId: 29271
- atomic: true
- Legal Obligation: mandatory
- PlainText: Figure 4: Establishment initiated by the RBC
- implement: false
- implementerEnhanced: Figure 4: Establishment initiated by the
  RBC
  [EXTERNAL]
- kind: Figure

##### 3.5.3.11 (Requirement Type)
In case the RBC is the initiator, the first message from RBC to on-board shall have the time-stamp and the LRBG identity set to "unknown".
- WordTraceId: 29341
- atomic: true
- Legal Obligation: mandatory
- implement: true
- implementerEnhanced: In case
  [CONDITION]
  the
  RBC
  [EXTERNAL]
  is the initiator, the first message from
  RBC
  [EXTERNAL]
  to on-board shall have the time-stamp and the
  LRBG
  [EXTERNAL]
  identity set to "unknown".
- kind: ordinary

##### 3.5.3.12 (Requirement Type)
Note: In the case the RBC is the initiator, there is no need to verify the compatibility of the system versions and for the on-board to send its telephone numbers, because the on-board is obviously already known to the RBC.
- WordTraceId: 29480
- atomic: false
- Legal Obligation: not applicable
- implement: false
- implementerEnhanced: Note: In the case the
  RBC
  [EXTERNAL]
  is the initiator, there is no need to verify the compatibility of the system versions and for the on-board to send its telephone numbers, because the on-board is
  obviously
  [WEAK]
  already known to the
  RBC
  [EXTERNAL]
  .
- kind: Note

##### 3.5.3.13 (Requirement Type)
An order to contact the RBC may contain a special value for the RBC identity indicating that the on-board shall contact the last known RBC (i.e., using the stored RBC ID/phone number, if any); the phone number indicated in the order shall be ignored by the on-board equipment.
- WordTraceId: 29704
- atomic: false
- Legal Obligation: optional
- implement: true
- implementerEnhanced: An order to contact the
  RBC
  [EXTERNAL]
  may contain a special value for the RBC identity indicating that the on-board shall contact the last known
  RBC
  [EXTERNAL]
  (i.e., using the stored RBC ID/phone number,
  if
  [CONDITION]
  any); the phone number indicated in the order shall be ignored by the
  on-board equipment
  [SELF]
  .
- kind: ordinary

###### 3.5.3.13.1 (Requirement Type)
If there is no RBC ID/ phone number stored on-board, the order to contact the RBC shall be ignored.
- WordTraceId: 29981
- atomic: true
- Legal Obligation: mandatory
- implement: true
- implementerEnhanced: If
  [CONDITION]
  there is no RBC ID/ phone number stored on-board, the order to contact the
  RBC
  [EXTERNAL]
  shall be ignored.
- kind: ordinary

##### 3.5.3.14 (Requirement Type)
Note: If a short number is used (considering trackside call routing), that number can be programmed into the balise instead of the normal phone number.
- WordTraceId: 30081
- atomic: false
- Legal Obligation: not applicable
- implement: false
- implementerEnhanced: Note:
  If
  [CONDITION]
  a short number is used (considering
  trackside
  [EXTERNAL]
  call routing), that number can be programmed into the
  balise
  [EXTERNAL]
  instead of the normal phone number.
- kind: Note

##### 3.5.3.15 (Requirement Type)
An order to contact the RBC may contain a special value for the RBC phone number indicating that the on-board shall use the on-board short number.
- WordTraceId: 30233
- atomic: false
- Legal Obligation: optional
- implement: true
- implementerEnhanced: An order to contact the
  RBC
  [EXTERNAL]
  may contain a special value for the
  RBC
  [EXTERNAL]
  phone number indicating that the on-board shall use the on-board short number.
- kind: ordinary

###### 3.5.3.15.1 (Requirement Type)
Note: The on-board stored short number for calling the RBC is defined by EIRENE.
- WordTraceId: 30380
- atomic: false
- Legal Obligation: not applicable
- implement: false
- implementerEnhanced: Note: The on-board stored short number for calling the
  RBC
  [EXTERNAL]
  is defined by EIRENE.
- kind: Note

##### 3.5.3.16 (Requirement Type)
- WordTraceId: 30461
- atomic: true
- Legal Obligation: unknown
- implement: true
- kind: ordinary

##### 3.5.3.16[2] (Requirement Type)
- WordTraceId: 30462
- atomic: false
- Legal Obligation: not applicable
- implement: false
- kind: Placeholder

###### 3.5.3.16[2].[t]* (Requirement Type)
| Option | Balise data content | Train reaction |
| --- | --- | --- |
| [r][2].[c][1] 1 | [r][2].[c][2] Order to contact RBC Special value for RBC ID: Contact last known RBC RBC Phone number irrelevant | [r][2].[c][3] Contact last known RBC (order is ignored in case no RBC ID/ phone number is stored on-board) |
| [r][3].[c][1] 2 | [r][3].[c][2] Order to contact RBC RBC ID Special value for RBC phone number: use on-board stored short number | [r][3].[c][3] Contact given RBC by using RBC ID and the on-board short number. Note: If the short number does not direct to the RBC with the given RBC ID, the connection will be terminated (EURORADIO functionality). |
| [r][4].[c][1] 3 | [r][4].[c][2] Order to contact RBC RBC ID + RBC phone number | [r][4].[c][3] Contact given RBC by using RBC ID and the RBC phone number |
- WordTraceId: 31113
- atomic: false
- Legal Obligation: not applicable
- implement: false
- kind: Table

###### 3.5.3.16[2].[t]*.[r][2] (Requirement Type)
- WordTraceId: 30505
- atomic: false
- Legal Obligation: not applicable
- implement: false
- kind: Table

###### 3.5.3.16[2].[t]*.[r][2].[c][1] (Requirement Type)
1
- WordTraceId: 30505
- atomic: true
- Legal Obligation: unknown
- implement: true
- kind: ordinary

###### 3.5.3.16[2].[t]*.[r][2].[c][2] (Requirement Type)
CONTENTS HAVE BEEN SPLIT UP - SEE CHILDREN
- WordTraceId: 30507
- atomic: false
- Legal Obligation: not applicable
- implement: false
- kind: ordinary

###### 3.5.3.16[2].[t]*.[r][2].[c][2].[1] (Requirement Type)
Order to contact RBC
- WordTraceId: 30507
- atomic: true
- Legal Obligation: unknown
- implement: true
- implementerEnhanced: Order to contact
  RBC
  [EXTERNAL]
- kind: ordinary

###### 3.5.3.16[2].[t]*.[r][2].[c][2].[2] (Requirement Type)
Special value for RBC ID:
Contact last known RBC
- WordTraceId: 30528
- atomic: true
- Legal Obligation: unknown
- implement: true
- implementerEnhanced: Special value for RBC ID: Contact last known
  RBC
  [EXTERNAL]
- kind: ordinary

###### 3.5.3.16[2].[t]*.[r][2].[c][2].[3] (Requirement Type)
RBC Phone number irrelevant
- WordTraceId: 30577
- atomic: true
- Legal Obligation: unknown
- implement: true
- implementerEnhanced: RBC
  [EXTERNAL]
  Phone number irrelevant
- kind: ordinary

###### 3.5.3.16[2].[t]*.[r][2].[c][3] (Requirement Type)
Contact last known RBC (order is ignored in case no RBC ID/ phone number is stored on-board)
- WordTraceId: 30605
- atomic: true
- Legal Obligation: unknown
- implement: true
- implementerEnhanced: Contact last known
  RBC
  [EXTERNAL]
  (order is ignored
  in case
  [CONDITION]
  no RBC ID/ phone number is stored on-board)
- kind: ordinary

###### 3.5.3.16[2].[t]*.[r][3] (Requirement Type)
- WordTraceId: 30699
- atomic: false
- Legal Obligation: not applicable
- implement: false
- kind: Table

###### 3.5.3.16[2].[t]*.[r][3].[c][1] (Requirement Type)
2
- WordTraceId: 30699
- atomic: true
- Legal Obligation: unknown
- implement: true
- kind: ordinary

###### 3.5.3.16[2].[t]*.[r][3].[c][2] (Requirement Type)
CONTENTS HAVE BEEN SPLIT UP - SEE CHILDREN
- WordTraceId: 30701
- atomic: false
- Legal Obligation: not applicable
- implement: false
- kind: ordinary

###### 3.5.3.16[2].[t]*.[r][3].[c][2].[1] (Requirement Type)
Order to contact RBC
- WordTraceId: 30701
- atomic: true
- Legal Obligation: unknown
- implement: true
- implementerEnhanced: Order to contact
  RBC
  [EXTERNAL]
- kind: ordinary

###### 3.5.3.16[2].[t]*.[r][3].[c][2].[2] (Requirement Type)
RBC ID
Special value for RBC phone number: use on-board stored short number
- WordTraceId: 30722
- atomic: true
- Legal Obligation: unknown
- implement: true
- implementerEnhanced: RBC ID Special value for
  RBC
  [EXTERNAL]
  phone number: use on-board stored short number
- kind: ordinary

###### 3.5.3.16[2].[t]*.[r][3].[c][3] (Requirement Type)
CONTENTS HAVE BEEN SPLIT UP - SEE CHILDREN
- WordTraceId: 30800
- atomic: false
- Legal Obligation: not applicable
- implement: false
- kind: ordinary

###### 3.5.3.16[2].[t]*.[r][3].[c][3].[1] (Requirement Type)
Contact given RBC by using RBC ID and the on-board short number.
- WordTraceId: 30800
- atomic: true
- Legal Obligation: unknown
- implement: true
- implementerEnhanced: Contact given
  RBC
  [EXTERNAL]
  by using RBC ID and the on-board short number.
- kind: ordinary

###### 3.5.3.16[2].[t]*.[r][3].[c][3].[2] (Requirement Type)
Note: If the short number does not direct to the RBC with the given RBC ID, the connection will be terminated (EURORADIO functionality).
- WordTraceId: 30865
- atomic: false
- Legal Obligation: not applicable
- implement: false
- implementerEnhanced: Note:
  If
  [CONDITION]
  the short number does not direct to the
  RBC
  [EXTERNAL]
  with the given RBC ID, the connection will be terminated (EURORADIO functionality).
- kind: Note

###### 3.5.3.16[2].[t]*.[r][4] (Requirement Type)
- WordTraceId: 31003
- atomic: false
- Legal Obligation: not applicable
- implement: false
- kind: Table

###### 3.5.3.16[2].[t]*.[r][4].[c][1] (Requirement Type)
3
- WordTraceId: 31003
- atomic: true
- Legal Obligation: unknown
- implement: true
- kind: ordinary

###### 3.5.3.16[2].[t]*.[r][4].[c][2] (Requirement Type)
CONTENTS HAVE BEEN SPLIT UP - SEE CHILDREN
- WordTraceId: 31005
- atomic: false
- Legal Obligation: not applicable
- implement: false
- kind: ordinary

###### 3.5.3.16[2].[t]*.[r][4].[c][2].[1] (Requirement Type)
Order to contact RBC
- WordTraceId: 31005
- atomic: true
- Legal Obligation: unknown
- implement: true
- implementerEnhanced: Order to contact
  RBC
  [EXTERNAL]
- kind: ordinary

###### 3.5.3.16[2].[t]*.[r][4].[c][2].[2] (Requirement Type)
RBC ID + RBC phone number
- WordTraceId: 31026
- atomic: true
- Legal Obligation: unknown
- implement: true
- implementerEnhanced: RBC ID +
  RBC
  [EXTERNAL]
  phone number
- kind: ordinary

###### 3.5.3.16[2].[t]*.[r][4].[c][3] (Requirement Type)
Contact given RBC by using RBC ID and the RBC phone number
- WordTraceId: 31052
- atomic: true
- Legal Obligation: unknown
- implement: true
- implementerEnhanced: Contact given
  RBC
  [EXTERNAL]
  by using RBC ID and the
  RBC
  [EXTERNAL]
  phone number
- kind: ordinary

#### 3.5.4 (Requirement Type)
Maintaining a communication session
- WordTraceId: 31113
- atomic: false
- Legal Obligation: not applicable
- implement: false
- kind: Heading

##### 3.5.4.1 (Requirement Type)
When a communication session is established, in case of a loss of the safe radio connection, i.e., if the disconnection has not been ordered (see 3.5.5.1), the involved entities shall consider the communication session still established for a defined time. The defined time shall start as soon as EURORADIO has indicated the loss of the safe radio connection.
- WordTraceId: 31149
- atomic: false
- Legal Obligation: mandatory
- implement: true
- implementerEnhanced: When
  [CONDITION]
  a communication session is established,
  in case of
  [CONDITION]
  a loss of the safe radio connection, i.e.,
  if
  [CONDITION]
  the disconnection has not been ordered (see 3.5.5.1), the involved entities shall consider the communication session still established for a
  defined
  time
  [TIME]
  [WEAK]
  . The
  defined
  time
  [TIME]
  [WEAK]
  shall start
  as soon as
  [WEAK]
  EURORADIO has indicated the loss of the safe radio connection.
- kind: ordinary
- CrossRefLink -> 3.5.5.1

##### 3.5.4.2 (Requirement Type)
When EURORADIO indicates the loss of the safe radio connection, the ERTMS/ETCS on-board equipment shall immediately try to set-up a new safe radio connection.
- WordTraceId: 31509
- atomic: true
- Legal Obligation: mandatory
- implement: true
- implementerEnhanced: When
  [CONDITION]
  EURORADIO indicates the loss of the safe radio connection, the
  ERTMS/ETCS on-board equipment
  [SELF]
  shall
  immediately
  [WEAK]
  try to set-up a new safe radio connection.
- kind: ordinary

###### 3.5.4.2.1 (Requirement Type)
If the safe radio connection is not re-established after the defined time (as defined in A3.1), both, on-board equipment and trackside, shall consider the session as terminated
.
- WordTraceId: 31668
- atomic: true
- Legal Obligation: mandatory
- PlainText: If the safe radio connection is not re-established after the defined time (as defined in A3.1), both, on-board equipment and trackside, shall consider the session as terminated.
- implement: true
- implementerEnhanced: If
  [CONDITION]
  the safe radio connection is not
  re-established
  [AGAIN]
  after
  [TIME]
  the
  defined
  time
  [TIME]
  [WEAK]
  (as defined in A3.1), both,
  on-board equipment
  [SELF]
  and
  trackside
  [EXTERNAL]
  , shall consider the session as terminated.
- kind: ordinary
- CrossRefLink -> A.3.1

##### 3.5.4.3 (Requirement Type)
The attempts shall be repeated, until at least one of the following conditions is met:
- WordTraceId: 31846
- atomic: true
- Legal Obligation: mandatory
- implement: true
- implementerEnhanced: The attempts shall be
  repeated
  [LOOP]
  ,
  until
  [TIME]
  at least
  [WEAK]
  one of the following conditions is met:
- kind: ordinary

###### 3.5.4.3.*[1] (Requirement Type)
The safe radio connection is set-up.
- WordTraceId: 31933
- atomic: true
- Legal Obligation: mandatory (>= 1)
- implement: true
- ListNumberText: ·
- kind: ordinary

###### 3.5.4.3.*[2] (Requirement Type)
The session is considered as terminated.
- WordTraceId: 31970
- atomic: true
- Legal Obligation: mandatory (>= 1)
- implement: true
- ListNumberText: ·
- kind: ordinary

###### 3.5.4.3.*[3] (Requirement Type)
The train passes the location indicated in the RIU order “Terminate the communication session”
- WordTraceId: 32011
- atomic: true
- Legal Obligation: mandatory (>= 1)
- implement: true
- implementerEnhanced: The train passes the location indicated in the
  RIU
  [EXTERNAL]
  order “Terminate the communication session”
- ListNumberText: ·
- kind: ordinary

###### 3.5.4.3.1 (Requirement Type)
Note: if the session is considered as terminated due to 3.5.4.2.1, the attempts will be resumed immediately according to 3.5.3.4 f).
- WordTraceId: 32106
- atomic: false
- Legal Obligation: mandatory (>= 1)
- implement: false
- implementerEnhanced: Note:
  if
  [CONDITION]
  the session is considered as terminated due to 3.5.4.2.1, the attempts will be resumed
  immediately
  [WEAK]
  according to 3.5.3.4 f).
- kind: Note
- CrossRefLink -> 3.5.4.2.1
- CrossRefLink -> 3.5.3.4.f

##### 3.5.4.4 (Requirement Type)
Exception to 3.5.4.2 and 3.5.4.3: the on-board equipment shall not try to set up a new safe radio connection and shall stop any on-going attempts if the train front is inside an announced radio hole (see 3.12.1.3). The on-board equipment shall try to set it up again when the train front reaches the end of the radio hole.
- WordTraceId: 32239
- atomic: false
- Legal Obligation: mandatory
- implement: true
- implementerEnhanced: Exception to 3.5.4.2 and 3.5.4.3: the
  on-board equipment
  [SELF]
  shall not try to set up a new safe radio connection and shall stop any on-going attempts
  if
  [CONDITION]
  the train front is inside an announced radio hole (see 3.12.1.3). The
  on-board equipment
  [SELF]
  shall try to set it up
  again
  [LOOP]
  when
  [CONDITION]
  the train front reaches the end of the radio hole.
- kind: ordinary
- CrossRefLink -> 3.5.4.2
- CrossRefLink -> 3.5.4.3
- CrossRefLink -> 3.12.1.3

##### 3.5.4.5 (Requirement Type)
In case a message has to be sent during the loss of the safe radio connection, this message shall be considered as sent.
- WordTraceId: 32562
- atomic: true
- Legal Obligation: mandatory
- implement: true
- implementerEnhanced: In case
  [CONDITION]
  a message has to be sent
  during
  [TIME]
  the loss of the safe radio connection, this message shall be considered as sent.
- kind: ordinary

#### 3.5.5 (Requirement Type)
Terminating a communication session
- WordTraceId: 32683
- atomic: false
- Legal Obligation: not applicable
- implement: false
- kind: Heading

##### 3.5.5.1 (Requirement Type)
The termination of a communication session shall be initiated only by the on-board and in the following cases:
- WordTraceId: 32719
- atomic: true
- Legal Obligation: mandatory
- implement: true
- kind: ordinary

###### 3.5.5.1.a (Requirement Type)
If an order is received from trackside (RBC, RIU or balise groups) (see sections 3.5.3.5 and 3.5.3.6 concerning the content of the order).
- WordTraceId: 32830
- atomic: true
- Legal Obligation: mandatory
- implement: true
- implementerEnhanced: If
  [CONDITION]
  an order is received from
  trackside
  [EXTERNAL]
  (
  RBC
  [EXTERNAL]
  ,
  RIU
  [EXTERNAL]
  or
  balise groups
  [EXTERNAL]
  ) (see sections 3.5.3.5 and 3.5.3.6 concerning the content of the order).
- ListNumberText: a)
- kind: ordinary
- CrossRefLink -> 3.5.3.5
- CrossRefLink -> 3.5.3.6

###### 3.5.5.1.b (Requirement Type)
If an error condition requiring the termination of the communication session is detected on-board (e.g., not compatible system versions between on-board and trackside).
- WordTraceId: 32969
- atomic: true
- Legal Obligation: mandatory
- implement: true
- implementerEnhanced: If
  [CONDITION]
  an error condition requiring the termination of the communication session is detected on-board (
  e.g.
  [WEAK]
  , not compatible system versions between on-board and
  trackside
  [EXTERNAL]
  ).
- ListNumberText: b)
- kind: ordinary

###### 3.5.5.1.c (Requirement Type)
The train is rejected by RBC during Start of Mission.
- WordTraceId: 33138
- atomic: true
- Legal Obligation: mandatory
- implement: true
- implementerEnhanced: The train is rejected by
  RBC
  [EXTERNAL]
  during
  [TIME]
  Start of Mission.
- ListNumberText: c)
- kind: ordinary

###### 3.5.5.1.d (Requirement Type)
If the driver closes the desk during Start of Mission.
- WordTraceId: 33192
- atomic: true
- Legal Obligation: mandatory
- implement: true
- implementerEnhanced: If
  [CONDITION]
  the
  driver
  [EXTERNAL]
  closes the desk
  during
  [TIME]
  Start of Mission.
- ListNumberText: d)
- kind: ordinary

###### 3.5.5.1.e (Requirement Type)
In case the train has reported having exited from an RBC area and no order to terminate the session is received within a fixed waiting time (see Appendix A.3.1) from the time the position report was sent, the ERTMS/ETCS on-board equipment shall repeatedly send a position report with the fixed waiting time after each repetition, until the order to terminate the session is received, or the defined number of repetitions (see Appendix A.3.1) has been reached. If no reply is received within the fixed waiting time after the last repetition, the ERTMS/ETCS on-board equipment shall terminate the communication session.
- WordTraceId: 33247
- atomic: false
- Legal Obligation: mandatory
- implement: true
- implementerEnhanced: In case
  [CONDITION]
  the train has reported having exited from an
  RBC
  [EXTERNAL]
  area and no order to terminate the session is received within a fixed
  waiting time
  [TIME]
  (see Appendix A.3.1) from the
  time
  [TIME]
  the position report was sent, the
  ERTMS/ETCS on-board equipment
  [SELF]
  shall
  repeatedly
  [LOOP]
  [WEAK]
  send a position report with the fixed
  waiting time
  [TIME]
  after
  [TIME]
  each
  repetition
  [LOOP]
  ,
  until
  [TIME]
  the order to terminate the session is received, or the defined number of
  repetitions
  [LOOP]
  (see Appendix A.3.1) has been reached.
  If
  [CONDITION]
  no reply is received within the fixed
  waiting time
  [TIME]
  after
  [TIME]
  the last
  repetition
  [LOOP]
  , the
  ERTMS/ETCS on-board equipment
  [SELF]
  shall
  terminate the communication session
  [LINKED_PHRASE]
  .
- ListNumberText: e)
- kind: ordinary
- CrossRefLink -> A.3.1
- KnownTermLink -> 3.5.4.3.*[3]

###### 3.5.5.1.f (Requirement Type)
In case of communication session with an RIU: the Level 1 is left, or, an End of Mission is executed.
- WordTraceId: 33865
- atomic: true
- Legal Obligation: mandatory
- implement: true
- implementerEnhanced: In case of
  [CONDITION]
  communication session with an
  RIU
  [EXTERNAL]
  : the Level 1 is left, or, an End of Mission is executed.
- ListNumberText: f)
- kind: ordinary

##### 3.5.5.2 (Requirement Type)
In case a session is established, the on-board equipment shall terminate the communication session according to the following steps:
- WordTraceId: 33967
- atomic: true
- Legal Obligation: not applicable
- implement: false
- implementerEnhanced: In case
  [CONDITION]
  a session is established, the
  on-board equipment
  [SELF]
  shall
  terminate the communication session
  [LINKED_PHRASE]
  according to the following steps:
- kind: Heading
- KnownTermLink -> 3.5.4.3.*[3]

###### 3.5.5.2.a (Requirement Type)
The on-board equipment shall send a Termination of communication session message.
- WordTraceId: 34100
- atomic: true
- Legal Obligation: mandatory
- implement: true
- implementerEnhanced: The
  on-board equipment
  [SELF]
  shall send a Termination of communication session message.
- ListNumberText: a)
- kind: ordinary

###### 3.5.5.2.b (Requirement Type)
As soon as this information is received, the trackside shall consider the communication session terminated and send an acknowledgement to the on-board.
- WordTraceId: 34183
- atomic: true
- Legal Obligation: mandatory
- implement: true
- implementerEnhanced: As soon as
  [WEAK]
  this information is received, the
  trackside
  [EXTERNAL]
  shall consider the communication session terminated and send an acknowledgement to the on-board.
- ListNumberText: b)
- kind: ordinary

###### 3.5.5.2.c (Requirement Type)
When the acknowledgement is received the on-board shall consider the communication session terminated and request the release of the safe radio connection with trackside.
- WordTraceId: 34335
- atomic: true
- Legal Obligation: mandatory
- implement: true
- implementerEnhanced: When
  [CONDITION]
  the acknowledgement is received the on-board shall consider the communication session terminated and request the release of the safe radio connection with
  trackside
  [EXTERNAL]
  .
- ListNumberText: c)
- kind: ordinary

###### 3.5.5.2.c[2] (Requirement Type)
- WordTraceId: 34507
- atomic: false
- Legal Obligation: not applicable
- implement: false
- kind: Placeholder

###### 3.5.5.2.c[2].[f]5 (Requirement Type)
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- WordTraceId: 34525
- atomic: false
- Legal Obligation: mandatory
- implement: false
- kind: Figure

###### 3.5.5.2.c[2].[f]5.C (Requirement Type)
Figure {Figure 5}: Termination of a communication session
- WordTraceId: 34525
- atomic: true
- Legal Obligation: mandatory
- PlainText: Figure 5: Termination of a communication session
- implement: false
- kind: Figure

##### 3.5.5.3 (Requirement Type)
No further message shall be sent by the on-board after the message Termination of communication session.
- WordTraceId: 34599
- atomic: true
- Legal Obligation: mandatory
- implement: true
- implementerEnhanced: No further message shall be sent by the on-board
  after
  [TIME]
  the message Termination of communication session.
- kind: ordinary

###### 3.5.5.3.1 (Requirement Type)
Exception: In case a communication session is established and no acknowledgement is received within a fixed waiting time (see Appendix A.3.1) after sending the “Termination of communication session” message, the message shall be repeated with the fixed waiting time after each repetition.
- WordTraceId: 34704
- atomic: true
- Legal Obligation: mandatory
- implement: true
- implementerEnhanced: Exception:
  In case
  [CONDITION]
  a communication session is established and no acknowledgement is received within a fixed
  waiting time
  [TIME]
  (see Appendix A.3.1)
  after
  [TIME]
  sending the “Termination of communication session” message, the message shall be
  repeated
  [LOOP]
  with the fixed
  waiting time
  [TIME]
  after
  [TIME]
  each
  repetition
  [LOOP]
  .
- kind: ordinary
- CrossRefLink -> A.3.1

###### 3.5.5.3.2 (Requirement Type)
After a defined number of repetitions (see Appendix A.3.1), and if no acknowledgment is received within the fixed waiting time from the time of the last sending of “Termination of communication session”, the ERTMS/ETCS onboard equipment shall consider the communication session terminated.
- WordTraceId: 34993
- atomic: true
- Legal Obligation: mandatory
- implement: true
- implementerEnhanced: After
  [TIME]
  a defined number of
  repetitions
  [LOOP]
  (see Appendix A.3.1), and
  if
  [CONDITION]
  no acknowledgment is received within the fixed
  waiting time
  [TIME]
  from the
  time
  [TIME]
  of the last sending of “
  Termination of communication session
  [LINKED_PHRASE]
  ”, the
  ERTMS/ETCS onboard equipment
  [SELF]
  shall consider the communication session terminated.
- kind: ordinary
- CrossRefLink -> A.3.1
- KnownTermLink -> 3.5.5.3.1

##### 3.5.5.4 (Requirement Type)
No further message shall be sent by the trackside after the message Acknowledgement of the termination of communication session.
- WordTraceId: 35283
- atomic: true
- Legal Obligation: mandatory
- implement: true
- implementerEnhanced: No further message shall be sent by the
  trackside
  [EXTERNAL]
  after
  [TIME]
  the message Acknowledgement of the
  termination of communication session
  [LINKED_PHRASE]
  .
- kind: ordinary
- KnownTermLink -> 3.5.5.3.1

##### 3.5.5.5 (Requirement Type)
The information Termination of Communication Session and corresponding Acknowledgement shall be the same in every system version.
- WordTraceId: 35412
- atomic: true
- Legal Obligation: mandatory
- implement: true
- implementerEnhanced: The information
  Termination of Communication Session
  [LINKED_PHRASE]
  and corresponding Acknowledgement shall be the same in every system version.
- kind: ordinary
- KnownTermLink -> 3.5.5.3.1

##### 3.5.5.6 (Requirement Type)
Messages from the RBC received onboard after the message “Termination of communication session” has been sent shall be ignored with the exception of the Acknowledgement of the termination of communication session.
- WordTraceId: 35542
- atomic: true
- Legal Obligation: mandatory
- implement: true
- implementerEnhanced: Messages from the
  RBC
  [EXTERNAL]
  received onboard
  after
  [TIME]
  the message “
  Termination of communication session
  [LINKED_PHRASE]
  ” has been sent shall be ignored with the exception of the Acknowledgement of the
  termination of communication session
  [LINKED_PHRASE]
  .
- kind: ordinary
- KnownTermLink -> 3.5.5.3.1

##### 3.5.5.7 (Requirement Type)
In case an order to terminate the communication session is received, while the communication session is currently being established, the on-board shall abort the process of establishing it and shall release the safe radio connection.
- WordTraceId: 35756
- atomic: false
- Legal Obligation: mandatory
- implement: true
- implementerEnhanced: In case
  [CONDITION]
  an order to
  terminate the communication session
  [LINKED_PHRASE]
  is received,
  while
  [TIME]
  the communication session is currently being established, the on-board shall abort the process of establishing it and shall release the safe radio connection.
- kind: ordinary
- KnownTermLink -> 3.5.4.3.*[3]

#### 3.5.6 (Requirement Type)
Registering to the Radio Network
- WordTraceId: 35990
- atomic: false
- Legal Obligation: not applicable
- implement: false
- kind: Heading

##### 3.5.6.1 (Requirement Type)
ERTMS/ETCS on-board equipment shall order the registration of its connected Mobile Terminal(s) to a Radio Network:
- WordTraceId: 36023
- atomic: true
- Legal Obligation: mandatory
- implement: true
- implementerEnhanced: ERTMS/ETCS on-board equipment
  [SELF]
  shall order the registration of its connected Mobile Terminal(s) to a Radio Network:
- kind: ordinary

###### 3.5.6.1.a (Requirement Type)
At power-up
- WordTraceId: 36138
- atomic: true
- Legal Obligation: unknown
- implement: true
- ListNumberText: a)
- kind: ordinary

###### 3.5.6.1.b (Requirement Type)
Following driver entry of a new Radio Network identity (only if level 2 or 3)
- WordTraceId: 36150
- atomic: true
- Legal Obligation: unknown
- implement: true
- implementerEnhanced: Following
  driver
  [EXTERNAL]
  entry of a new Radio Network identity (only
  if
  [CONDITION]
  level 2 or 3)
- ListNumberText: b)
- kind: ordinary

###### 3.5.6.1.c (Requirement Type)
If ordered from the trackside
- WordTraceId: 36228
- atomic: true
- Legal Obligation: unknown
- implement: true
- implementerEnhanced: If
  [CONDITION]
  ordered from the
  trackside
  [EXTERNAL]
- ListNumberText: c)
- kind: ordinary

##### 3.5.6.2 (Requirement Type)
When powered-off, ERTMS/ETCS on-board equipment shall memorize the last received Radio Network identity (from trackside or from driver) and shall use it when powered-up again.
- WordTraceId: 36258
- atomic: false
- Legal Obligation: mandatory
- implement: true
- implementerEnhanced: When
  [CONDITION]
  powered-off,
  ERTMS/ETCS on-board equipment
  [SELF]
  shall memorize the last received Radio Network identity (from
  trackside
  [EXTERNAL]
  or from
  driver
  [EXTERNAL]
  ) and shall use it
  when
  [CONDITION]
  powered-up
  again
  [LOOP]
  .
- kind: ordinary

##### 3.5.6.3 (Requirement Type)
If no Radio Network identity received from trackside or from driver could have been memorized by ERTMS/ETCS on-board equipment (e.g. after a System Failure or at very first power-up), this latter shall nevertheless order the registration of its Mobile Terminal(s) to a default Radio Network.
- WordTraceId: 36434
- atomic: true
- Legal Obligation: mandatory
- implement: true
- implementerEnhanced: If
  [CONDITION]
  no Radio Network identity received from
  trackside
  [EXTERNAL]
  or from
  driver
  [EXTERNAL]
  could have been memorized by
  ERTMS/ETCS on-board equipment
  [SELF]
  (
  e.g.
  [WEAK]
  after
  [TIME]
  a System Failure or at very first power-up), this latter shall nevertheless order the registration of its Mobile Terminal(s) to a default Radio Network.
- kind: ordinary

###### 3.5.6.3.1 (Requirement Type)
Note 1: the source used to retrieve the default Radio Network identity (on-board equipment permanent storage, Mobile Terminal itself, or other external source) is implementation dependent.
- WordTraceId: 36726
- atomic: false
- Legal Obligation: not applicable
- implement: false
- implementerEnhanced: Note 1: the source used to retrieve the default Radio Network identity (
  on-board equipment
  [SELF]
  permanent storage, Mobile Terminal itself, or other
  external
  [EXTERNAL]
  source) is implementation dependent.
- kind: Note

###### 3.5.6.3.2 (Requirement Type)
Note 2: if ERTMS/ETCS on-board equipment is powered-up in an area not covered by the memorized or default Radio Network, attempts to register to this Radio Network will be repeated unconditionally by the Mobile Terminal(s) until either an attempt is successful or a new Radio Network identity is received from trackside or from driver, preventing Mobile Terminal(s) from registering to any unwanted Radio Network
.
- WordTraceId: 36916
- atomic: false
- Legal Obligation: not applicable
- PlainText: Note 2: if ERTMS/ETCS on-board equipment is powered-up in an area not covered by the memorized or default Radio Network, attempts to register to this Radio Network will be repeated unconditionally by the Mobile Terminal(s) until either an attempt is successful or a new Radio Network identity is received from trackside or from driver, preventing Mobile Terminal(s) from registering to any unwanted Radio Network.
- implement: false
- implementerEnhanced: Note 2:
  if
  [CONDITION]
  ERTMS/ETCS on-board equipment
  [SELF]
  is powered-up in an area not covered by the memorized or default Radio Network, attempts to register to this Radio Network will be
  repeated
  [LOOP]
  unconditionally by the Mobile Terminal(s)
  until
  [TIME]
  either an attempt is successful or a new Radio Network identity is received from
  trackside
  [EXTERNAL]
  or from
  driver
  [EXTERNAL]
  , preventing Mobile Terminal(s) from registering to any unwanted Radio Network.
- kind: Note

##### 3.5.6.4 (Requirement Type)
Note: for Radio Network identity data entry by driver during SoM, please refer to chapter 5 (Procedure Start of Mission).
- WordTraceId: 37330
- atomic: false
- Legal Obligation: not applicable
- implement: false
- implementerEnhanced: Note: for Radio Network identity data entry by
  driver
  [EXTERNAL]
  during
  [TIME]
  SoM, please refer to chapter 5 (Procedure Start of Mission).
- kind: Note

##### 3.5.6.5 (Requirement Type)
On reception of the trackside order, ERTMS/ETCS on-board equipment shall immediately order the Radio Network registration of each Mobile Terminal that fulfils the following conditions:
- WordTraceId: 37452
- atomic: true
- Legal Obligation: not applicable
- implement: false
- implementerEnhanced: On reception of the
  trackside
  [EXTERNAL]
  order,
  ERTMS/ETCS on-board equipment
  [SELF]
  shall
  immediately
  [WEAK]
  order the Radio Network registration of each Mobile Terminal that fulfils the following conditions:
- kind: Heading

###### 3.5.6.5.a (Requirement Type)
it is not yet registered to the ordered Radio Network, AND
- WordTraceId: 37637
- atomic: true
- Legal Obligation: mandatory
- implement: true
- implementerEnhanced: it is
  not yet
  [TIME]
  registered to the ordered Radio Network, AND
- ListNumberText: a)
- kind: ordinary

###### 3.5.6.5.b (Requirement Type)
it is not used for an established communication session, AND
- WordTraceId: 37696
- atomic: true
- Legal Obligation: mandatory
- implement: true
- ListNumberText: b)
- kind: ordinary

###### 3.5.6.5.c (Requirement Type)
no safe radio connection is being set-up
- WordTraceId: 37757
- atomic: true
- Legal Obligation: mandatory
- implement: true
- ListNumberText: c)
- kind: ordinary

##### 3.5.6.6 (Requirement Type)
If a Mobile Terminal is not currently registered to the Radio Network ordered by trackside and if one of the conditions b) or c) is not fulfilled, ERTMS/ETCS on-board equipment shall initiate the Radio Network registration once communication session is terminated and safe radio connection is released.
- WordTraceId: 37798
- atomic: true
- Legal Obligation: mandatory
- implement: true
- implementerEnhanced: If
  [CONDITION]
  a Mobile Terminal is not currently registered to the Radio Network ordered by
  trackside
  [EXTERNAL]
  and
  if
  [CONDITION]
  one of the conditions b) or c) is not fulfilled,
  ERTMS/ETCS on-board equipment
  [SELF]
  shall initiate the Radio Network registration
  once communication session is terminated
  [WEAK]
  and safe radio connection is released.
- kind: ordinary

##### 3.5.6.7 (Requirement Type)
If no Mobile Terminal is duly registered to a Radio Network, any order to contact an RBC or an RIU received from trackside shall be rejected by ERTMS/ETCS on-board equipment.
- WordTraceId: 38101
- atomic: true
- Legal Obligation: mandatory
- implement: true
- implementerEnhanced: If
  [CONDITION]
  no Mobile Terminal is duly registered to a Radio Network, any order to contact an
  RBC
  [EXTERNAL]
  or an
  RIU
  [EXTERNAL]
  received from
  trackside
  [EXTERNAL]
  shall be rejected by
  ERTMS/ETCS on-board equipment
  [SELF]
  .
- kind: ordinary

#### 3.5.7 (Requirement Type)
Safe Radio Connection Indication
- WordTraceId: 38276
- atomic: false
- Legal Obligation: not applicable
- implement: false
- kind: Heading

##### 3.5.7.1 (Requirement Type)
The ERTMS/ETCS on-board equipment shall inform the driver about the status of the safe radio connection. To that purpose, the following indication statuses of the safe radio connection are defined: “No Connection”, “Connection Lost/Set-Up failed”, “Connection Up”.
- WordTraceId: 38309
- atomic: false
- Legal Obligation: mandatory
- implement: true
- implementerEnhanced: The
  ERTMS/ETCS on-board equipment
  [SELF]
  shall inform the
  driver
  [EXTERNAL]
  about the status of the safe radio connection. To that purpose, the following indication statuses of the safe radio connection are defined: “No Connection”, “Connection Lost/Set-Up failed”, “Connection Up”.
- kind: ordinary

##### 3.5.7.2 (Requirement Type)
In addition, the ERTMS/ETCS on-board equipment shall use a “connection status” timer (see Appendix A.3.1), in order to manage properly the transitions to the indication status “Connection Lost/Set-Up failed”.
- WordTraceId: 38574
- atomic: true
- Legal Obligation: mandatory
- implement: true
- implementerEnhanced: In addition, the
  ERTMS/ETCS on-board equipment
  [SELF]
  shall use a “connection status”
  timer
  [TIME]
  (see Appendix A.3.1), in order to manage properly the transitions to the indication status “
  Connection Lost/Set-Up failed
  [LINKED_PHRASE]
  ”.
- kind: ordinary
- CrossRefLink -> A.3.1
- KnownTermLink -> 3.5.7.1

###### 3.5.7.2.1 (Requirement Type)
Note: The purpose of the “connection status” timer is to avoid distracting the driver for any short disturbance of the safe radio connection.
- WordTraceId: 38783
- atomic: false
- Legal Obligation: not applicable
- implement: false
- implementerEnhanced: Note: The purpose of the “
  connection status
  [LINKED_PHRASE]
  ”
  timer
  [TIME]
  is to avoid distracting the
  driver
  [EXTERNAL]
  for any short disturbance of the safe radio connection.
- kind: Note
- KnownTermLink -> 3.5.7.2

##### 3.5.7.3 (Requirement Type)
The ERTMS/ETCS on-board equipment shall start the “connection status” timer as soon as the first request to set-up a safe radio connection with the relevant RBC/RIU is sent:
- WordTraceId: 38925
- atomic: true
- Legal Obligation: mandatory
- implement: true
- implementerEnhanced: The
  ERTMS/ETCS on-board equipment
  [SELF]
  shall start the “
  connection status
  [LINKED_PHRASE]
  ”
  timer
  [TIME]
  as soon as
  [WEAK]
  the first request to set-up a safe radio connection with the relevant
  RBC
  [EXTERNAL]
  /
  RIU
  [EXTERNAL]
  is sent:
- kind: ordinary
- KnownTermLink -> 3.5.7.2

###### 3.5.7.3.a (Requirement Type)
for what regards the session establishment, see items b), c), d), e) in 3.5.3.4.
- WordTraceId: 39099
- atomic: true
- Legal Obligation: unknown
- implement: true
- ListNumberText: a)
- kind: ordinary
- CrossRefLink -> 3.5.3.4.b
- CrossRefLink -> 3.5.3.4.c
- CrossRefLink -> 3.5.3.4.d
- CrossRefLink -> 3.5.3.4.e

###### 3.5.7.3.b (Requirement Type)
for what regards maintaining a communication session, see 3.5.4.2 and 3.5.4.4
- WordTraceId: 39180
- atomic: true
- Legal Obligation: unknown
- implement: true
- ListNumberText: b)
- kind: ordinary
- CrossRefLink -> 3.5.4.2
- CrossRefLink -> 3.5.4.4

##### 3.5.7.4 (Requirement Type)
If the “connection status” timer is ongoing, it shall be stopped if the requests to set-up a safe radio connection are stopped with the relevant RBC/RIU.
- WordTraceId: 39258
- atomic: true
- Legal Obligation: mandatory
- implement: true
- implementerEnhanced: If
  [CONDITION]
  the “
  connection status
  [LINKED_PHRASE]
  ”
  timer
  [TIME]
  is ongoing, it shall be stopped
  if
  [CONDITION]
  the requests to set-up a safe radio connection are stopped with the relevant
  RBC
  [EXTERNAL]
  /
  RIU
  [EXTERNAL]
  .
- kind: ordinary
- KnownTermLink -> 3.5.7.2

##### 3.5.7.5 (Requirement Type)
The ERTMS/ETCS on-board equipment shall execute the transitions between the different indication statuses of the safe radio connection with the relevant RBC/RIU as described in Table 1 according to the conditions in Table 2 (see section 4.6.1 for details about the symbols).
- WordTraceId: 39412
- atomic: true
- Legal Obligation: mandatory
- implement: true
- implementerEnhanced: The
  ERTMS/ETCS on-board equipment
  [SELF]
  shall execute the transitions between the different indication statuses of the safe radio connection with the relevant
  RBC
  [EXTERNAL]
  /
  RIU
  [EXTERNAL]
  as described in Table 1 according to the conditions in Table 2 (see section 4.6.1 for details about the symbols).
- kind: ordinary
- CrossRefLink -> 3.5.7.5[2].[t]1.C
- CrossRefLink -> 3.5.7.5[3].[t]2.C
- CrossRefLink -> 4.6.1

##### 3.5.7.5[2] (Requirement Type)
- WordTraceId: 39739
- atomic: false
- Legal Obligation: not applicable
- implement: false
- kind: Placeholder

###### 3.5.7.5[2].[t]1 (Requirement Type)
| No Connection | [r][1].ConnectionLostSet-Upfailed_NoConnection < 3 -p2- | [r][1].ConnectionUp_NoConnection < 5, 6, 7 -p1- |
| --- | --- | --- |
| [r][2].NoConnection_ConnectionLostSet-Upfailed 1, 2 > -p2- | Connection Lost / Set-Up failed | [r][2].ConnectionUp_ConnectionLostSet-Upfailed <2 -p2- |
| [r][3].NoConnection_ConnectionUp 4 > -p1- | [r][3].ConnectionLostSet-Upfailed_ConnectionUp 4 > -p1- | Connection Up |
- WordTraceId: 39864
- atomic: false
- Legal Obligation: not applicable
- implement: false
- kind: Table

###### 3.5.7.5[2].[t]1.C (Requirement Type)
Table {Table 1}: Transitions between the indication statuses of the safe radio connection
- WordTraceId: 39864
- atomic: true
- Legal Obligation: unknown
- PlainText: Table 1: Transitions between the indication statuses of the safe radio connection
- implement: false
- kind: Table

###### 3.5.7.5[2].[t]1.[r][1] (Requirement Type)
- WordTraceId: 39739
- atomic: false
- Legal Obligation: not applicable
- implement: false
- kind: Table

###### 3.5.7.5[2].[t]1.[r][1].ConnectionLostSet-Upfailed_NoConnection (Requirement Type)
< 3
-p2-
- WordTraceId: 39753
- atomic: true
- Legal Obligation: unknown
- PlainText: < 3 -p2-
- implement: true
- kind: ordinary

###### 3.5.7.5[2].[t]1.[r][1].ConnectionUp_NoConnection (Requirement Type)
< 5, 6, 7
-p1-
- WordTraceId: 39762
- atomic: true
- Legal Obligation: unknown
- PlainText: < 5, 6, 7 -p1-
- implement: true
- kind: ordinary

###### 3.5.7.5[2].[t]1.[r][2] (Requirement Type)
- WordTraceId: 39778
- atomic: false
- Legal Obligation: not applicable
- implement: false
- kind: Table

###### 3.5.7.5[2].[t]1.[r][2].NoConnection_ConnectionLostSet-Upfailed (Requirement Type)
1, 2 >
-p2-
- WordTraceId: 39778
- atomic: true
- Legal Obligation: unknown
- PlainText: 1, 2 > -p2-
- implement: true
- kind: ordinary

###### 3.5.7.5[2].[t]1.[r][2].ConnectionUp_ConnectionLostSet-Upfailed (Requirement Type)
<2
-p2-
- WordTraceId: 39822
- atomic: true
- Legal Obligation: unknown
- PlainText: <2 -p2-
- implement: true
- kind: ordinary

###### 3.5.7.5[2].[t]1.[r][3] (Requirement Type)
- WordTraceId: 39831
- atomic: false
- Legal Obligation: not applicable
- implement: false
- kind: Table

###### 3.5.7.5[2].[t]1.[r][3].NoConnection_ConnectionUp (Requirement Type)
4 >
-p1-
- WordTraceId: 39831
- atomic: true
- Legal Obligation: unknown
- PlainText: 4 > -p1-
- implement: true
- kind: ordinary

###### 3.5.7.5[2].[t]1.[r][3].ConnectionLostSet-Upfailed_ConnectionUp (Requirement Type)
4 >
-p1-
- WordTraceId: 39840
- atomic: true
- Legal Obligation: unknown
- PlainText: 4 > -p1-
- implement: true
- kind: ordinary

##### 3.5.7.5[3] (Requirement Type)
- WordTraceId: 39971
- atomic: false
- Legal Obligation: not applicable
- implement: false
- kind: Placeholder

###### 3.5.7.5[3].[t]2 (Requirement Type)
| Condition Id | Content of the conditions |
| --- | --- |
| [1] | [C]1.Content (a Start of mission procedure is on-going) AND (the final attempt to set-up the safe radio connection failed) |
| [2] | [C]2.Content (the “connection status” timer expires) |
| [3] | [C]3.Content (no Start of mission procedure is on-going) AND (the requests to set-up a safe radio connection are stopped with the relevant RBC/RIU for reason other than the successful set-up) |
| [4] | [C]4.Content (the safe radio connection is set-up) |
| [5] | [C]5.Content (the safe radio connection is released) |
| [6] | [C]6.Content (the safe radio connection is lost) AND (the requests to set-up a safe radio connection are stopped with the relevant RBC/RIU for reason other than the successful set-up) |
| [7] | [C]7.Content (the safe radio connection is lost) AND (the train front is inside an announced radio hole) |
- WordTraceId: 40716
- atomic: false
- Legal Obligation: not applicable
- implement: false
- kind: Table

###### 3.5.7.5[3].[t]2.C (Requirement Type)
Table {Table 2}: Transition conditions for the indication statuses of the safe radio connection
- WordTraceId: 40716
- atomic: true
- Legal Obligation: unknown
- PlainText: Table 2: Transition conditions for the indication statuses of the safe radio connection
- implement: false
- kind: Table

###### 3.5.7.5[3].[t]2.[C]1 (Requirement Type)
- WordTraceId: 40011
- atomic: false
- Legal Obligation: not applicable
- implement: false
- kind: Table

###### 3.5.7.5[3].[t]2.[C]1.Content (Requirement Type)
(a Start of mission procedure is on-going) AND (the final attempt to set-up the safe radio connection failed)
- WordTraceId: 40015
- atomic: true
- Legal Obligation: unknown
- implement: true
- kind: ordinary

###### 3.5.7.5[3].[t]2.[C]2 (Requirement Type)
- WordTraceId: 40126
- atomic: false
- Legal Obligation: not applicable
- implement: false
- kind: Table

###### 3.5.7.5[3].[t]2.[C]2.Content (Requirement Type)
(the “connection status” timer expires)
- WordTraceId: 40130
- atomic: true
- Legal Obligation: unknown
- implement: true
- implementerEnhanced: (the “
  connection status
  [LINKED_PHRASE]
  ”
  timer
  [TIME]
  expires)
- kind: ordinary
- KnownTermLink -> 3.5.7.2

###### 3.5.7.5[3].[t]2.[C]3 (Requirement Type)
- WordTraceId: 40171
- atomic: false
- Legal Obligation: not applicable
- implement: false
- kind: Table

###### 3.5.7.5[3].[t]2.[C]3.Content (Requirement Type)
(no Start of mission procedure is on-going) AND (the requests to set-up a safe radio connection are stopped with the relevant RBC/RIU for reason other than the successful set-up)
- WordTraceId: 40175
- atomic: true
- Legal Obligation: unknown
- implement: true
- implementerEnhanced: (no Start of mission procedure is on-going) AND (the requests to set-up a safe radio connection are stopped with the relevant
  RBC
  [EXTERNAL]
  /
  RIU
  [EXTERNAL]
  for reason other than the successful set-up)
- kind: ordinary

###### 3.5.7.5[3].[t]2.[C]4 (Requirement Type)
- WordTraceId: 40355
- atomic: false
- Legal Obligation: not applicable
- implement: false
- kind: Table

###### 3.5.7.5[3].[t]2.[C]4.Content (Requirement Type)
(the safe radio connection is set-up)
- WordTraceId: 40359
- atomic: true
- Legal Obligation: unknown
- implement: true
- kind: ordinary

###### 3.5.7.5[3].[t]2.[C]5 (Requirement Type)
- WordTraceId: 40398
- atomic: false
- Legal Obligation: not applicable
- implement: false
- kind: Table

###### 3.5.7.5[3].[t]2.[C]5.Content (Requirement Type)
(the safe radio connection is released)
- WordTraceId: 40402
- atomic: true
- Legal Obligation: unknown
- implement: true
- kind: ordinary

###### 3.5.7.5[3].[t]2.[C]6 (Requirement Type)
- WordTraceId: 40443
- atomic: false
- Legal Obligation: not applicable
- implement: false
- kind: Table

###### 3.5.7.5[3].[t]2.[C]6.Content (Requirement Type)
(the safe radio connection is lost) AND (the requests to set-up a safe radio connection are stopped with the relevant RBC/RIU for reason other than the successful set-up)
- WordTraceId: 40447
- atomic: true
- Legal Obligation: unknown
- implement: true
- implementerEnhanced: (the safe radio connection is lost) AND (the requests to set-up a safe radio connection are stopped with the relevant
  RBC
  [EXTERNAL]
  /
  RIU
  [EXTERNAL]
  for reason other than the successful set-up)
- kind: ordinary

###### 3.5.7.5[3].[t]2.[C]7 (Requirement Type)
- WordTraceId: 40619
- atomic: false
- Legal Obligation: not applicable
- implement: false
- kind: Table

###### 3.5.7.5[3].[t]2.[C]7.Content (Requirement Type)
(the safe radio connection is lost) AND (the train front is inside an announced radio hole)
- WordTraceId: 40623
- atomic: true
- Legal Obligation: unknown
- implement: true
- kind: ordinary

##### 3.5.7.6 (Requirement Type)
For the case of an RBC/RBC transition, the safe radio connection indicated to the driver shall switch from the indication status of the safe radio connection with the Handing over RBC to the one with the Accepting RBC as soon as one of the following conditions is met:
- WordTraceId: 40828
- atomic: true
- Legal Obligation: mandatory
- implement: true
- implementerEnhanced: For the case of an
  RBC
  [EXTERNAL]
  /
  RBC
  [EXTERNAL]
  transition, the safe radio connection indicated to the
  driver
  [EXTERNAL]
  shall switch from the indication status of the safe radio connection with the Handing over
  RBC
  [EXTERNAL]
  to the one with the Accepting
  RBC
  [EXTERNAL]
  as soon as
  [WEAK]
  one of the following conditions is met:
- kind: ordinary

###### 3.5.7.6.a (Requirement Type)
the ERTMS/ETCS on-board equipment sends a position report directly to the Accepting RBC with its maximum safe front end having passed the border, see 3.15.1.3.5 (i.e. the Accepting RBC becomes the supervising RBC),
- WordTraceId: 41097
- atomic: true
- Legal Obligation: mandatory (== 1)
- implement: true
- implementerEnhanced: the
  ERTMS/ETCS on-board equipment
  [SELF]
  sends a position report directly to the Accepting
  RBC
  [EXTERNAL]
  with its maximum safe front end having passed the border, see 3.15.1.3.5 (i.e. the Accepting
  RBC
  [EXTERNAL]
  becomes the supervising
  RBC
  [EXTERNAL]
  ),
- ListNumberText: a)
- kind: ordinary
- CrossRefLink -> 3.15.1.3.5

###### 3.5.7.6.b (Requirement Type)
the safe radio connection is released with the Handing over RBC and the minimum safe rear end of the train has crossed the border, see 3.5.5.1 e) and 3.15.1.2.7.
- WordTraceId: 41312
- atomic: true
- Legal Obligation: mandatory (== 1)
- implement: true
- implementerEnhanced: the safe radio connection is released with the Handing over
  RBC
  [EXTERNAL]
  and the minimum safe rear end of the train has crossed the border, see 3.5.5.1 e) and 3.15.1.2.7.
- ListNumberText: b)
- kind: ordinary
- CrossRefLink -> 3.5.5.1.e
- CrossRefLink -> 3.15.1.2.7

###### 3.5.7.6.1 (Requirement Type)
Note: During an RBC/RBC handover procedure, an indication status transition table and a connection status timer might have to be managed at the same time, for each RBC.
- WordTraceId: 41474
- atomic: false
- Legal Obligation: mandatory (== 1)
- implement: false
- implementerEnhanced: Note:
  During
  [TIME]
  an
  RBC
  [EXTERNAL]
  /
  RBC
  [EXTERNAL]
  handover procedure, an indication status transition table and a
  connection status
  [LINKED_PHRASE]
  timer
  [TIME]
  might have to be managed at the same
  time
  [TIME]
  ,
  for each
  [LOOP]
  RBC
  [EXTERNAL]
  .
- kind: Note
- KnownTermLink -> 3.5.7.2

##### 3.5.7.7 (Requirement Type)
For the case of safe radio connection with RIU’s, the safe radio connection indicated to the driver shall be the one related to the current infill area.
- WordTraceId: 41643
- atomic: true
- Legal Obligation: mandatory
- implement: true
- implementerEnhanced: For the case of safe radio connection with RIU’s, the safe radio connection indicated to the
  driver
  [EXTERNAL]
  shall be the one related to the current infill area.
- kind: ordinary

### 3.6 (Requirement Type)
Location Principles, Train Position and Train Orientation
- WordTraceId: 41796
- atomic: false
- Legal Obligation: not applicable
- implement: false
- kind: Heading

#### 3.6.1 (Requirement Type)
General
- WordTraceId: 41854
- atomic: false
- Legal Obligation: not applicable
- implement: false
- kind: Heading

##### 3.6.1.1 (Requirement Type)
It shall be possible to identify:
- WordTraceId: 41862
- atomic: true
- Legal Obligation: mandatory
- implement: true
- kind: ordinary

###### 3.6.1.1.a (Requirement Type)
Data that refers only to a given location, referred to as Location data (e.g. level transition orders, linking)
- WordTraceId: 41896
- atomic: true
- Legal Obligation: unknown
- implement: true
- implementerEnhanced: Data that refers only to a given location, referred to as Location data (
  e.g.
  [WEAK]
  level transition orders, linking)
- ListNumberText: a)
- kind: ordinary

###### 3.6.1.1.b (Requirement Type)
Data that remains valid for a certain distance, referred to as Profile data (e.g. SSP, gradient).
- WordTraceId: 42008
- atomic: false
- Legal Obligation: unknown
- implement: true
- implementerEnhanced: Data that remains valid for a certain distance, referred to as Profile data (
  e.g.
  [WEAK]
  SSP, gradient).
- ListNumberText: b)
- kind: ordinary

##### 3.6.1.2 (Requirement Type)
Note: Determination of the Train Position is always longitudinal along the route, even though the route might be set through a complex track layout.
- WordTraceId: 42107
- atomic: false
- Legal Obligation: not applicable
- implement: false
- kind: Note

##### 3.6.1.2[2] (Requirement Type)
- WordTraceId: 42256
- atomic: false
- Legal Obligation: not applicable
- implement: false
- kind: Placeholder

###### 3.6.1.2[2].[f]6 (Requirement Type)
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- WordTraceId: 42279
- atomic: false
- Legal Obligation: not applicable
- implement: false
- kind: Figure

###### 3.6.1.2[2].[f]6.C (Requirement Type)
Figure {Figure 6}: Actual route of the train
- WordTraceId: 42279
- atomic: true
- Legal Obligation: unknown
- PlainText: Figure 6: Actual route of the train
- implement: false
- implementerEnhanced: Figure 6: Actual route of the train
- kind: Figure

##### 3.6.1.2[3] (Requirement Type)
- WordTraceId: 42342
- atomic: false
- Legal Obligation: not applicable
- implement: false
- kind: Placeholder

###### 3.6.1.2[3].[f]7 (Requirement Type)
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- WordTraceId: 42366
- atomic: false
- Legal Obligation: not applicable
- implement: false
- kind: Figure

###### 3.6.1.2[3].[f]7.C (Requirement Type)
Figure {Figure 7}: Route known by the train
- WordTraceId: 42366
- atomic: true
- Legal Obligation: unknown
- PlainText: Figure 7: Route known by the train
- implement: false
- implementerEnhanced: Figure 7: Route known by the train
- kind: Figure

##### 3.6.1.3 (Requirement Type)
The Train Position information defines the position of the train front in relation to a balise group, which is called LRBG (the Last Relevant Balise Group). It includes:
- WordTraceId: 42428
- atomic: false
- Legal Obligation: unknown
- implement: false
- implementerEnhanced: The Train Position information defines the position of the train front in relation to a
  balise group
  [EXTERNAL]
  , which is called
  LRBG
  [EXTERNAL]
  (the
  Last Relevant Balise Group
  [EXTERNAL]
  ). It includes:
- kind: Definition

###### 3.6.1.3.*[1] (Requirement Type)
The estimated train front end position, defined by the estimated distance between the LRBG and the front end of the train
- WordTraceId: 42598
- atomic: true
- Legal Obligation: unknown
- implement: false
- implementerEnhanced: The estimated train front end position, defined by the estimated distance between the
  LRBG
  [EXTERNAL]
  and the front end of the train
- ListNumberText: ·
- kind: Definition

###### 3.6.1.3.*[2] (Requirement Type)
The train position confidence interval (see 3.6.4)
- WordTraceId: 42720
- atomic: true
- Legal Obligation: unknown
- implement: false
- ListNumberText: ·
- kind: Definition
- CrossRefLink -> 3.6.4

###### 3.6.1.3.*[3] (Requirement Type)
Directional train position information in reference to the balise group orientation (see 3.4.2, also Figure 14) of the LRBG, regarding:
- WordTraceId: 42771
- atomic: true
- Legal Obligation: unknown
- implement: false
- implementerEnhanced: Directional train position information in reference to the
  balise group
  [EXTERNAL]
  orientation (see 3.4.2, also Figure 14) of the
  LRBG
  [EXTERNAL]
  , regarding:
- ListNumberText: ·
- kind: Definition
- CrossRefLink -> 3.4.2
- CrossRefLink -> 3.6.5.1.2[2].[f]14.C

###### 3.6.1.3.*[3].*[1] (Requirement Type)
the position of the train front end (nominal or reverse side of the LRBG)
- WordTraceId: 42907
- atomic: true
- Legal Obligation: unknown
- implement: false
- implementerEnhanced: the position of the train front end (nominal or reverse side of the
  LRBG
  [EXTERNAL]
  )
- ListNumberText: -
- kind: Definition

###### 3.6.1.3.*[3].*[2] (Requirement Type)
the train orientation
- WordTraceId: 42981
- atomic: true
- Legal Obligation: unknown
- implement: false
- ListNumberText: -
- kind: Definition

###### 3.6.1.3.*[3].*[3] (Requirement Type)
the train running direction
- WordTraceId: 43004
- atomic: true
- Legal Obligation: unknown
- implement: false
- ListNumberText: -
- kind: Definition

###### 3.6.1.3.*[3][2] (Requirement Type)
In case of an LRBG being a single balise group with no co-ordinate system assigned, directional information is defined in reference to the pair of LRBG and “previous LRBG”, see 3.4.2.3.3
- WordTraceId: 43032
- atomic: true
- Legal Obligation: unknown
- implement: false
- implementerEnhanced: In case of
  [CONDITION]
  an
  LRBG
  [EXTERNAL]
  being a single
  balise group
  [EXTERNAL]
  with no co-ordinate system assigned, directional information is defined in reference to the pair of
  LRBG
  [EXTERNAL]
  and “
  previous
  LRBG
  [EXTERNAL]
  [LINKED_PHRASE]
  ”, see 3.4.2.3.3
- kind: Definition
- CrossRefLink -> 3.4.2.3.3
- KnownTermLink -> 3.4.2.3.3.1

###### 3.6.1.3.*[4] (Requirement Type)
A list of LRBGs, which may alternatively be used by trackside for referencing location dependent information (see 3.6.2.2.2 c)).
- WordTraceId: 43219
- atomic: true
- Legal Obligation: optional
- implement: true
- implementerEnhanced: A list of
  LRBGs
  [EXTERNAL]
  , which may alternatively be used by
  trackside
  [EXTERNAL]
  for referencing location dependent information (see 3.6.2.2.2 c)).
- ListNumberText: ·
- kind: ordinary
- CrossRefLink -> 3.6.2.2.2.c

##### 3.6.1.4 (Requirement Type)
Balise groups, which are marked as unlinked, shall never be used as LRBG.
- WordTraceId: 43348
- atomic: true
- Legal Obligation: mandatory
- implement: true
- implementerEnhanced: Balise groups
  [EXTERNAL]
  , which are marked as unlinked, shall never be used as
  LRBG
  [EXTERNAL]
  .
- kind: ordinary

###### 3.6.1.4.1 (Requirement Type)
Justification: The location of an unlinked balise group, or the balise group itself, may not be known to the RBC.
- WordTraceId: 43422
- atomic: false
- Legal Obligation: optional
- implement: false
- implementerEnhanced: Justification: The location of an unlinked
  balise group
  [EXTERNAL]
  , or the
  balise group
  [EXTERNAL]
  itself, may not be known to the
  RBC
  [EXTERNAL]
  .
- kind: Justification

##### 3.6.1.5 (Requirement Type)
If there is an active cab, this one defines the orientation of the train, i.e. the side of the active cab shall be considered as the front of the train. If no cab is active, the train orientation shall be as when a cab was last active.
- WordTraceId: 43536
- atomic: false
- Legal Obligation: mandatory
- implement: false
- implementerEnhanced: If
  [CONDITION]
  there is an active cab, this one defines the orientation of the train, i.e. the side of the active cab shall be considered as the front of the train.
  If
  [CONDITION]
  no cab is active, the train orientation shall be as
  when
  [CONDITION]
  a cab was last active.
- kind: Definition

##### 3.6.1.6 (Requirement Type)
The “train orientation relative to LRBG” is defined as the train orientation related to the orientation of the LRBG, see Figure 14. It can be either “nominal” or “reverse”.
- WordTraceId: 43772
- atomic: false
- Legal Obligation: unknown
- implement: false
- implementerEnhanced: The “train orientation relative to
  LRBG
  [EXTERNAL]
  ” is defined as the train orientation related to the orientation of the
  LRBG
  [EXTERNAL]
  , see Figure 14. It can be either “nominal” or “reverse”.
- kind: Definition
- CrossRefLink -> 3.6.5.1.2[2].[f]14.C

###### 3.6.1.6.1 (Requirement Type)
Note: The train orientation cannot be affected by the direction controller position.
- WordTraceId: 43966
- atomic: false
- Legal Obligation: not applicable
- implement: false
- kind: Note

#### 3.6.2 (Requirement Type)
Location of Data Transmitted to the On-Board Equipment
- WordTraceId: 44051
- atomic: false
- Legal Obligation: not applicable
- implement: false
- implementerEnhanced: Location of Data Transmitted to the
  On-Board Equipment
  [SELF]
- kind: Heading

##### 3.6.2.1 (Requirement Type)
Data Transmitted by Balises
- WordTraceId: 44106
- atomic: false
- Legal Obligation: not applicable
- implement: false
- implementerEnhanced: Data Transmitted by
  Balises
  [EXTERNAL]
- kind: Heading

###### 3.6.2.1.1 (Requirement Type)
All location and profile data transmitted by a balise shall refer to the location reference and orientation of the balise group to which the balise belongs.
- WordTraceId: 44134
- atomic: true
- Legal Obligation: mandatory
- implement: true
- implementerEnhanced: All location and profile data transmitted by a
  balise
  [EXTERNAL]
  shall refer to the location reference and orientation of the
  balise group
  [EXTERNAL]
  to which the
  balise
  [EXTERNAL]
  belongs.
- kind: ordinary

###### 3.6.2.1.2 (Requirement Type)
Exception: Regarding infill information see section 3.6.2.3.1.
- WordTraceId: 44291
- atomic: true
- Legal Obligation: unknown
- implement: true
- kind: ordinary
- CrossRefLink -> 3.6.2.3.1

##### 3.6.2.2 (Requirement Type)
Data Transmitted by Radio from RBC
- WordTraceId: 44383
- atomic: false
- Legal Obligation: not applicable
- implement: false
- implementerEnhanced: Data Transmitted by Radio from
  RBC
  [EXTERNAL]
- kind: Heading

###### 3.6.2.2.1 (Requirement Type)
All location and profile data transmitted from the RBC shall refer to the location reference and orientation of the LRBG given in the same message.
- WordTraceId: 44418
- atomic: true
- Legal Obligation: mandatory
- implement: true
- implementerEnhanced: All location and profile data transmitted from the
  RBC
  [EXTERNAL]
  shall refer to the location reference and orientation of the
  LRBG
  [EXTERNAL]
  given in the same message.
- kind: ordinary

###### 3.6.2.2.2 (Requirement Type)
For the LRBG the following requirements have to be met:
- WordTraceId: 44566
- atomic: true
- Legal Obligation: unknown
- implement: false
- implementerEnhanced: For the
  LRBG
  [EXTERNAL]
  the following requirements have to be met:
- kind: Heading

###### 3.6.2.2.2.a (Requirement Type)
The on-board equipment shall use the last balise group passed as a reference when reporting its position to the RBC (in the following termed as LRBG
ONB
). Only
- WordTraceId: 44622
- atomic: false
- Legal Obligation: mandatory
- PlainText: The on-board equipment shall use the last balise group passed as a reference when reporting its position to the RBC (in the following termed as LRBGONB). Only
- implement: true
- implementerEnhanced: The
  on-board equipment
  [SELF]
  shall use the last
  balise group
  [EXTERNAL]
  passed as a reference
  when
  [CONDITION]
  reporting its position to the
  RBC
  [EXTERNAL]
  (in the following termed as LRBGONB). Only
- ListNumberText: a)
- kind: ordinary

###### 3.6.2.2.2.a.*[1] (Requirement Type)
balise groups marked as linked and contained in the previously received linking information, if linking information is used on-board
- WordTraceId: 44782
- atomic: true
- Legal Obligation: unknown
- implement: true
- implementerEnhanced: balise groups
  [EXTERNAL]
  marked as linked and contained in the previously received linking information,
  if
  [CONDITION]
  linking information is used
  [LINKED_PHRASE]
  on-board
- ListNumberText: ·
- kind: ordinary
- KnownTermLink -> 3.4.4.2.1.1

###### 3.6.2.2.2.a[2] (Requirement Type)
or
- WordTraceId: 44915
- atomic: true
- Legal Obligation: unknown
- implement: true
- kind: ordinary

###### 3.6.2.2.2.a[2].*[1] (Requirement Type)
the last balise group not marked as unlinked, if no linking was used when this balise group was passed
- WordTraceId: 44920
- atomic: true
- Legal Obligation: unknown
- implement: true
- implementerEnhanced: the last
  balise group
  [EXTERNAL]
  not marked as unlinked,
  if
  [CONDITION]
  no linking was used
  when
  [CONDITION]
  this
  balise group
  [EXTERNAL]
  was passed
- ListNumberText: ·
- kind: ordinary

###### 3.6.2.2.2.a[3] (Requirement Type)
shall be regarded.
- WordTraceId: 45023
- atomic: true
- Legal Obligation: mandatory
- implement: true
- kind: ordinary

###### 3.6.2.2.2.b (Requirement Type)
The RBC shall use the
last
relevant balise group which was reported by the on-board equipment as a reference (in the following termed as LRBG
RBC
). At a certain moment LRBG
RBC
and LRBG
ONB
can be different.
- WordTraceId: 45042
- atomic: false
- Legal Obligation: mandatory
- PlainText: The RBC shall use the last relevant balise group which was reported by the on-board equipment as a reference (in the following termed as LRBGRBC). At a certain moment LRBGRBC and LRBGONB can be different.
- implement: true
- implementerEnhanced: The
  RBC
  [EXTERNAL]
  shall use the
  last relevant balise group
  [EXTERNAL]
  which was reported by the
  on-board equipment
  [SELF]
  as a reference (in the following termed as LRBGRBC). At a
  certain moment
  [WEAK]
  LRBGRBC and LRBGONB can be different.
- ListNumberText: b)
- kind: ordinary

###### 3.6.2.2.2.c (Requirement Type)
The on-board equipment shall be able to accept information referring to one of at least eight LRBG
ONB
last reported to the RBC.
- WordTraceId: 45247
- atomic: true
- Legal Obligation: mandatory
- PlainText: The on-board equipment shall be able to accept information referring to one of at least eight LRBGONB last reported to the RBC.
- implement: true
- implementerEnhanced: The
  on-board equipment
  [SELF]
  shall be able to accept information referring to one of
  at least
  [WEAK]
  eight LRBGONB last reported to the
  RBC
  [EXTERNAL]
  .
- ListNumberText: c)
- kind: ordinary

###### 3.6.2.2.2.1 (Requirement Type)
Exception to a): When on-board position is unknown or when position data has been deleted during SoM procedure, the on-board equipment shall use an LRBG identifier set to "unknown" until the onboard has validated its position again by passing a balise group.
- WordTraceId: 45375
- atomic: true
- Legal Obligation: mandatory
- implement: true
- implementerEnhanced: Exception to a):
  When
  [CONDITION]
  on-board position is unknown or
  when
  [CONDITION]
  position data has been deleted
  during
  [TIME]
  SoM procedure, the
  on-board equipment
  [SELF]
  shall use an
  LRBG
  [EXTERNAL]
  identifier set to "unknown"
  until
  [TIME]
  the onboard has validated its position
  again
  [LOOP]
  by passing a
  balise group
  [EXTERNAL]
  .
- kind: ordinary
- CrossRefLink -> 3.6.2.2.2.a

###### 3.6.2.2.2.2 (Requirement Type)
Exception to b): When the RBC has received from the onboard an unknown position, or an invalid position which it is not able to confirm during SoM procedure, the RBC shall use an LRBG identifier set to "unknown" until it receives a position report from the onboard having validated its position by passing a balise group.
- WordTraceId: 45634
- atomic: true
- Legal Obligation: mandatory
- implement: true
- implementerEnhanced: Exception to b):
  When
  [CONDITION]
  the
  RBC
  [EXTERNAL]
  has received from the onboard an unknown position, or an invalid position which it is not able to confirm
  during
  [TIME]
  SoM procedure, the
  RBC
  [EXTERNAL]
  shall use an
  LRBG
  [EXTERNAL]
  identifier set to "unknown"
  until
  [TIME]
  it receives a position report from the onboard having validated its position by passing a
  balise group
  [EXTERNAL]
  .
- kind: ordinary
- CrossRefLink -> 3.6.2.2.2.b

###### 3.6.2.2.2.3 (Requirement Type)
Regarding c): From the time it has reported an unknown position, or an invalid position during SoM procedure, to the time it has received from the RBC a message with an LRBG not set to “unknown”, the on-board equipment shall also be able to accept messages from the RBC containing LRBG “unknown”.
- WordTraceId: 45956
- atomic: true
- Legal Obligation: mandatory
- implement: true
- implementerEnhanced: Regarding c): From the
  time
  [TIME]
  it has reported an unknown position, or an invalid position
  during
  [TIME]
  SoM procedure, to the
  time
  [TIME]
  it has received from the
  RBC
  [EXTERNAL]
  a message with an
  LRBG
  [EXTERNAL]
  not set to “unknown”, the
  on-board equipment
  [SELF]
  shall also be able to accept messages from the
  RBC
  [EXTERNAL]
  containing
  LRBG
  [EXTERNAL]
  “unknown”.
- kind: ordinary
- CrossRefLink -> 3.6.2.2.2.c

###### 3.6.2.2.3 (Requirement Type)
Example: The following figure illustrates the on-board and RBC views of LRBGs:
- WordTraceId: 46253
- atomic: false
- Legal Obligation: not applicable
- implement: false
- implementerEnhanced: Example: The following figure illustrates the on-board and
  RBC
  [EXTERNAL]
  views of
  LRBGs
  [EXTERNAL]
  :
- kind: Example

###### 3.6.2.2.3[2] (Requirement Type)
- WordTraceId: 46332
- atomic: false
- Legal Obligation: not applicable
- implement: false
- kind: Placeholder

###### 3.6.2.2.3[2].[f]8 (Requirement Type)
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- WordTraceId: 46357
- atomic: false
- Legal Obligation: not applicable
- implement: false
- kind: Figure

###### 3.6.2.2.3[2].[f]8.C (Requirement Type)
Figure {Figure 8}: On-board and RBC views of LRBG when train is reporting new LRBG ONB "D"
- WordTraceId: 46357
- atomic: true
- Legal Obligation: unknown
- PlainText: Figure 8: On-board and RBC views of LRBG when train is reporting new LRBGONB "D"
- implement: false
- implementerEnhanced: Figure 8: On-board and
  RBC
  [EXTERNAL]
  views of
  LRBG
  [EXTERNAL]
  when
  [CONDITION]
  train is reporting new LRBGONB "D"
- kind: Figure

##### 3.6.2.3 (Requirement Type)
Data transmitted as Infill information
- WordTraceId: 46465
- atomic: false
- Legal Obligation: not applicable
- implement: false
- kind: Heading

###### 3.6.2.3.1 (Requirement Type)
All location and profile data transmitted as infill information shall refer to the location reference of the balise group at the next main signal (identified by the infill information) and to the orientation given by the infill device. (See note after justification).
- WordTraceId: 46504
- atomic: true
- Legal Obligation: mandatory
- implement: true
- implementerEnhanced: All location and profile data transmitted as infill information shall refer to the location reference of the
  balise group
  [EXTERNAL]
  at the next main signal (identified by the infill information) and to the orientation given by the infill device. (See note
  after
  [TIME]
  justification).
- kind: ordinary

###### 3.6.2.3.1.1 (Requirement Type)
Justification:
- WordTraceId: 46772
- atomic: false
- Legal Obligation: not applicable
- implement: false
- kind: Justification

###### 3.6.2.3.1.1.*[1] (Requirement Type)
At locations where routes join: Infill information is the same for all routes, only linking information is different for different routes, see figure below (infill by means of balise group(s), loop or radio)
- WordTraceId: 46787
- atomic: true
- Legal Obligation: unknown
- implement: false
- implementerEnhanced: At locations where routes join: Infill information is the same
  for all
  [LOOP]
  routes, only linking information is different for different routes, see figure
  below
  [WEAK]
  (infill by means of
  balise group(s)
  [EXTERNAL]
  ,
  loop
  [EXTERNAL]
  or radio)
- ListNumberText: ·
- kind: Justification

###### 3.6.2.3.1.1.*[1][2] (Requirement Type)
- WordTraceId: 46995
- atomic: false
- Legal Obligation: not applicable
- implement: false
- kind: Placeholder

###### 3.6.2.3.1.1.*[1][2].[f]9 (Requirement Type)
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- WordTraceId: 47025
- atomic: false
- Legal Obligation: not applicable
- implement: false
- kind: Figure

###### 3.6.2.3.1.1.*[1][2].[f]9.C (Requirement Type)
Figure {Figure 9}: Routes Join in Rear of InFill Area
- WordTraceId: 47025
- atomic: true
- Legal Obligation: unknown
- PlainText: Figure 9: Routes Join in Rear of InFill Area
- implement: false
- kind: Figure

###### 3.6.2.3.1.1.*[2] (Requirement Type)
In case of an infill area with multiple balise groups: all balise groups transmit identical information, as the information of all groups refers to the balise group at the main signal.
- WordTraceId: 47095
- atomic: true
- Legal Obligation: unknown
- implement: false
- implementerEnhanced: In case of
  [CONDITION]
  an infill area with multiple
  balise groups
  [EXTERNAL]
  : all
  balise groups
  [EXTERNAL]
  transmit identical information, as the information of all groups refers to the
  balise group
  [EXTERNAL]
  at the main signal.
- ListNumberText: ·
- kind: Justification

###### 3.6.2.3.1.1.*[2][2] (Requirement Type)
- WordTraceId: 47280
- atomic: false
- Legal Obligation: not applicable
- implement: false
- kind: Placeholder

###### 3.6.2.3.1.1.*[2][2].[f]10 (Requirement Type)
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- WordTraceId: 47310
- atomic: false
- Legal Obligation: not applicable
- implement: false
- kind: Figure

###### 3.6.2.3.1.1.*[2][2].[f]10.C (Requirement Type)
Figure {Figure 10}
:
Location referencing of infill information transmitted by balise groups
- WordTraceId: 47310
- atomic: true
- Legal Obligation: unknown
- PlainText: Figure 10: Location referencing of infill information transmitted by balise groups
- implement: false
- implementerEnhanced: Figure 10: Location referencing of infill information transmitted by
  balise groups
  [EXTERNAL]
- kind: Figure

###### 3.6.2.3.1.2 (Requirement Type)
Note: The orientation of infill information given by an infill device is defined in reference to (see also section 3.9):
- WordTraceId: 47419
- atomic: false
- Legal Obligation: not applicable
- implement: false
- kind: Note
- CrossRefLink -> 3.9

###### 3.6.2.3.1.2.*[1] (Requirement Type)
In case of a balise group, the orientation of the balise group sending the infill information
- WordTraceId: 47540
- atomic: true
- Legal Obligation: unknown
- implement: false
- implementerEnhanced: In case of
  [CONDITION]
  a
  balise group
  [EXTERNAL]
  , the orientation of the
  balise group
  [EXTERNAL]
  sending the infill information
- ListNumberText: ·
- kind: Note

###### 3.6.2.3.1.2.*[2] (Requirement Type)
In case of loop, the orientation indicated by the End Of Loop Marker
- WordTraceId: 47635
- atomic: true
- Legal Obligation: unknown
- implement: false
- implementerEnhanced: In case of
  [CONDITION]
  loop
  [EXTERNAL]
  , the orientation indicated by the End Of
  Loop
  [EXTERNAL]
  Marker
- ListNumberText: ·
- kind: Note

###### 3.6.2.3.1.2.*[3] (Requirement Type)
In case of radio, the orientation of the LRBG indicated in the message
- WordTraceId: 47704
- atomic: true
- Legal Obligation: unknown
- implement: false
- implementerEnhanced: In case of
  [CONDITION]
  radio, the orientation of the
  LRBG
  [EXTERNAL]
  indicated in the message
- ListNumberText: ·
- kind: Note

##### 3.6.2.4 (Requirement Type)
Data transmitted by Loop
- WordTraceId: 47776
- atomic: false
- Legal Obligation: not applicable
- implement: false
- implementerEnhanced: Data transmitted by
  Loop
  [EXTERNAL]
- kind: Heading

###### 3.6.2.4.1 (Requirement Type)
It shall be possible to transmit non-infill location data by loop, which refers to a balise group as location reference.
- WordTraceId: 47801
- atomic: true
- Legal Obligation: mandatory
- implement: true
- implementerEnhanced: It shall be possible to transmit non-infill location data by
  loop
  [EXTERNAL]
  , which refers to a
  balise group
  [EXTERNAL]
  as location reference.
- kind: ordinary

###### 3.6.2.4.1.1 (Requirement Type)
Note: Regarding infill information see section 3.6.2.3.
- WordTraceId: 47922
- atomic: false
- Legal Obligation: not applicable
- implement: false
- kind: Note
- CrossRefLink -> 3.6.2.3

###### 3.6.2.4.2 (Requirement Type)
The orientation of data transmitted by a loop is determined by the EOLM information which indicates how the directional information contained in loop messages is to be interpreted.
- WordTraceId: 47978
- atomic: true
- Legal Obligation: unknown
- implement: true
- implementerEnhanced: The orientation of data transmitted by a
  loop
  [EXTERNAL]
  is determined by the EOLM information which indicates how the directional information contained in
  loop
  [EXTERNAL]
  messages is to be interpreted.
- kind: ordinary

#### 3.6.3 (Requirement Type)
Validity direction of transmitted Information
- WordTraceId: 48159
- atomic: false
- Legal Obligation: not applicable
- implement: false
- kind: Heading

##### 3.6.3.1 (Requirement Type)
General
- WordTraceId: 48205
- atomic: false
- Legal Obligation: not applicable
- implement: false
- kind: Heading

###### 3.6.3.1.1 (Requirement Type)
The direction for which transmitted information is valid shall refer to:
- WordTraceId: 48213
- atomic: true
- Legal Obligation: mandatory
- implement: true
- kind: ordinary

###### 3.6.3.1.1.a (Requirement Type)
the direction of the LRBG for information sent by radio
- WordTraceId: 48286
- atomic: true
- Legal Obligation: unknown
- implement: true
- implementerEnhanced: the direction of the
  LRBG
  [EXTERNAL]
  for information sent by radio
- ListNumberText: a)
- kind: ordinary

###### 3.6.3.1.1.b (Requirement Type)
the direction of the balise group sending the information.
- WordTraceId: 48342
- atomic: true
- Legal Obligation: unknown
- implement: true
- implementerEnhanced: the direction of the
  balise group
  [EXTERNAL]
  sending the information.
- ListNumberText: b)
- kind: ordinary

###### 3.6.3.1.2 (Requirement Type)
Data transmitted to the on-board equipment (by balise or radio) shall be identified as being valid for
- WordTraceId: 48401
- atomic: true
- Legal Obligation: mandatory
- implement: true
- implementerEnhanced: Data transmitted to the
  on-board equipment
  [SELF]
  (by
  balise
  [EXTERNAL]
  or radio) shall be identified as being valid for
- kind: ordinary

###### 3.6.3.1.2.a (Requirement Type)
both directions
- WordTraceId: 48504
- atomic: true
- Legal Obligation: unknown
- implement: true
- ListNumberText: a)
- kind: ordinary

###### 3.6.3.1.2.b (Requirement Type)
the nominal direction
- WordTraceId: 48520
- atomic: true
- Legal Obligation: unknown
- implement: true
- ListNumberText: b)
- kind: ordinary

###### 3.6.3.1.2.c (Requirement Type)
the reverse direction
- WordTraceId: 48542
- atomic: true
- Legal Obligation: unknown
- implement: true
- ListNumberText: c)
- kind: ordinary

###### 3.6.3.1.2[2] (Requirement Type)
of the referenced balise group.
- WordTraceId: 48564
- atomic: true
- Legal Obligation: unknown
- implement: true
- implementerEnhanced: of the referenced
  balise group
  [EXTERNAL]
  .
- kind: ordinary

###### 3.6.3.1.2[2].1 (Requirement Type)
Deleted.
- WordTraceId: 48596
- atomic: false
- Legal Obligation: not applicable
- implement: false
- ListNumberText: 3.6.3.1.2.1
- kind: Placeholder

###### 3.6.3.1.3 (Requirement Type)
When receiving information from any transmission medium, the ERTMS/ETCS on-board equipment shall only take into account information valid for its orientation. Other information shall be ignored. Exception: for SL, PS and SH engines, balise group crossing direction shall be considered.
- WordTraceId: 48605
- atomic: false
- Legal Obligation: mandatory
- implement: true
- implementerEnhanced: When
  [CONDITION]
  receiving information from any transmission medium, the
  ERTMS/ETCS on-board equipment
  [SELF]
  shall only take into account information valid for its orientation. Other information shall be ignored. Exception: for SL, PS and SH engines,
  balise group
  [EXTERNAL]
  crossing direction shall be considered.
- kind: ordinary

###### 3.6.3.1.3.1 (Requirement Type)
If the train position is unknown, data received from any transmission medium valid for one direction only (nominal or reverse) shall be rejected by the onboard equipment. Data valid for both directions shall be evaluated (see section 4.8).
- WordTraceId: 48891
- atomic: false
- Legal Obligation: mandatory
- implement: true
- implementerEnhanced: If
  [CONDITION]
  the train position is unknown, data received from any transmission medium valid for one direction only (nominal or reverse) shall be rejected by the
  onboard equipment
  [SELF]
  . Data valid for both directions shall be evaluated (see section 4.8).
- kind: ordinary
- CrossRefLink -> 4.8

###### 3.6.3.1.4 (Requirement Type)
If no co-ordinate system has been assigned to a single balise group, data transmitted by trackside, which refers to that balise group requiring the co-ordinate system to be known (i.e. all data which are only valid for one direction (nominal or reverse)) shall be rejected by the ERTMS/ETCS on-board equipment. Data valid for both directions shall be evaluated (see section 4.8).
- WordTraceId: 49131
- atomic: false
- Legal Obligation: mandatory
- implement: true
- implementerEnhanced: If
  [CONDITION]
  no co-ordinate system has been assigned to a single
  balise group
  [EXTERNAL]
  , data transmitted by
  trackside
  [EXTERNAL]
  , which refers to that
  balise group
  [EXTERNAL]
  requiring the co-ordinate system to be known (i.e. all data which are only valid for one direction (nominal or reverse)) shall be rejected by the
  ERTMS/ETCS on-board equipment
  [SELF]
  . Data valid for both directions shall be evaluated (see section 4.8).
- kind: ordinary
- CrossRefLink -> 4.8

###### 3.6.3.1.4.1 (Requirement Type)
Exception: if not rejected due to balise group message consistency check (see 3.16.2.4.4.1 and 3.16.2.5.1.1), data to be forwarded to a National System (see section 3.15.6) shall be accepted. Justification: the co-ordinate system of the balise group might be known to the National System by other means inherent to the National System itself.
- WordTraceId: 49511
- atomic: false
- Legal Obligation: mandatory
- implement: true
- implementerEnhanced: Exception:
  if
  [CONDITION]
  not rejected due to
  balise group
  [EXTERNAL]
  message consistency check (see 3.16.2.4.4.1 and 3.16.2.5.1.1), data to be forwarded to a
  National System
  [EXTERNAL]
  (see section 3.15.6) shall be accepted. Justification: the co-ordinate system of the
  balise group
  [EXTERNAL]
  might be known to the
  National System
  [EXTERNAL]
  by other means inherent to the
  National System
  [EXTERNAL]
  itself.
- kind: ordinary
- CrossRefLink -> 3.16.2.4.4.1
- CrossRefLink -> 3.16.2.5.1.1
- CrossRefLink -> 3.15.6

###### 3.6.3.1.4.1[2] (Requirement Type)
Figure {Figure 11}: Intentionally deleted
- WordTraceId: 49854
- atomic: false
- Legal Obligation: not applicable
- PlainText: Figure 11: Intentionally deleted
- implement: false
- implementerEnhanced: Figure 11: Intentionally deleted
- kind: Placeholder

##### 3.6.3.2 (Requirement Type)
Location, Continuous Profile Data and Non-continuous Profile Data
- WordTraceId: 49912
- atomic: false
- Legal Obligation: not applicable
- implement: false
- kind: Heading

###### 3.6.3.2.1 (Requirement Type)
Location and profile data shall have the structure shown in Figure 12 below
- WordTraceId: 49978
- atomic: true
- Legal Obligation: mandatory
- implement: true
- implementerEnhanced: Location and profile data shall have the structure shown in Figure 12
  below
  [WEAK]
- kind: ordinary
- CrossRefLink -> 3.6.3.2.1[2].[f]12.C

###### 3.6.3.2.1[2] (Requirement Type)
- WordTraceId: 50096
- atomic: false
- Legal Obligation: not applicable
- implement: false
- kind: Placeholder

###### 3.6.3.2.1[2].[f]12 (Requirement Type)
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- WordTraceId: 50127
- atomic: false
- Legal Obligation: not applicable
- implement: false
- kind: Figure

###### 3.6.3.2.1[2].[f]12.C (Requirement Type)
Figure {Figure 12}: General Structure of location and profile data
- WordTraceId: 50127
- atomic: true
- Legal Obligation: unknown
- PlainText: Figure 12: General Structure of location and profile data
- implement: false
- kind: Figure

###### 3.6.3.2.2 (Requirement Type)
With regard to Figure 12 the following applies to continuous profile data:
- WordTraceId: 50210
- atomic: true
- Legal Obligation: unknown
- implement: false
- kind: Heading
- CrossRefLink -> 3.6.3.2.1[2].[f]12.C

###### 3.6.3.2.2.a (Requirement Type)
Value (n) shall be valid for distance (n+1)
- WordTraceId: 50327
- atomic: true
- Legal Obligation: mandatory
- implement: true
- ListNumberText: a)
- kind: ordinary

###### 3.6.3.2.2.b (Requirement Type)
For distance (1) the previously received data shall be used (in case of an SSP this includes train length delay, refer to 3.11.3.1.3).
- WordTraceId: 50372
- atomic: true
- Legal Obligation: mandatory
- implement: true
- implementerEnhanced: For distance (1) the previously received data shall be used (
  in case of
  [CONDITION]
  an SSP this includes train length
  delay
  [TIME]
  , refer to 3.11.3.1.3).
- ListNumberText: b)
- kind: ordinary
- CrossRefLink -> 3.11.3.1.3

###### 3.6.3.2.2.c (Requirement Type)
Distances shall be given as unsigned incremental values representing the distance between value(n) and value(n-1).
- WordTraceId: 50507
- atomic: true
- Legal Obligation: mandatory
- implement: true
- ListNumberText: c)
- kind: ordinary

###### 3.6.3.2.2.d (Requirement Type)
The last value (n) transmitted shall be valid for an unlimited distance unless value(n) represents a special "end of profile" value.
- WordTraceId: 50622
- atomic: true
- Legal Obligation: mandatory
- implement: true
- ListNumberText: d)
- kind: ordinary

###### 3.6.3.2.2.e (Requirement Type)
If distance (n+1) = 0 then the corresponding profile value n shall still be taken into account.
- WordTraceId: 50755
- atomic: true
- Legal Obligation: mandatory
- implement: true
- implementerEnhanced: If
  [CONDITION]
  distance (n+1) = 0 then the corresponding profile value n shall still be taken into account.
- ListNumberText: e)
- kind: ordinary

###### 3.6.3.2.3 (Requirement Type)
With regard to Figure 12 the following shall apply to location data:
- WordTraceId: 50851
- atomic: true
- Legal Obligation: not applicable
- implement: false
- kind: Heading
- CrossRefLink -> 3.6.3.2.1[2].[f]12.C

###### 3.6.3.2.3.a (Requirement Type)
Distances shall be given as unsigned incremental values representing the distance between value(n) and value(n-1).
- WordTraceId: 50962
- atomic: true
- Legal Obligation: mandatory
- implement: true
- ListNumberText: a)
- kind: ordinary

###### 3.6.3.2.3.b (Requirement Type)
For distance (1) the previously received data shall be used.
- WordTraceId: 51077
- atomic: true
- Legal Obligation: mandatory
- implement: true
- ListNumberText: b)
- kind: ordinary

###### 3.6.3.2.3.c (Requirement Type)
Each value (n) may represent a single value or a set of data.
- WordTraceId: 51138
- atomic: true
- Legal Obligation: mandatory
- implement: true
- ListNumberText: c)
- kind: ordinary

###### 3.6.3.2.4 (Requirement Type)
According to Figure 12 the structure for non-continuous profile data shall allow to contain multiple elements (value(n) for length(n)) inside the profile.
- WordTraceId: 51200
- atomic: true
- Legal Obligation: mandatory
- implement: true
- kind: ordinary
- CrossRefLink -> 3.6.3.2.1[2].[f]12.C

###### 3.6.3.2.4.a (Requirement Type)
Distance to the start of each element (value(n) for length(n)) shall be given as unsigned incremental values, each increment representing the distance between starts of element (n) and element (n-1).
- WordTraceId: 51398
- atomic: true
- Legal Obligation: mandatory
- implement: true
- ListNumberText: a)
- kind: ordinary

###### 3.6.3.2.4.b (Requirement Type)
For distance (1) the previously received data (or initial data/default values, see section 3.7) shall be used.
- WordTraceId: 51599
- atomic: true
- Legal Obligation: mandatory
- implement: true
- ListNumberText: b)
- kind: ordinary
- CrossRefLink -> 3.7

###### 3.6.3.2.4.c (Requirement Type)
Each value (n) may represent a single value or a set of data.
- WordTraceId: 51739
- atomic: true
- Legal Obligation: optional
- implement: true
- ListNumberText: c)
- kind: ordinary

###### 3.6.3.2.4.d (Requirement Type)
Note: There is no relationship between length of element (n-1) and distance (n), i.e., elements may overlap.
- WordTraceId: 51802
- atomic: false
- Legal Obligation: optional
- implement: false
- ListNumberText: d)
- kind: Note

###### 3.6.3.2.5 (Requirement Type)
It shall be possible for the RBC to shift the location reference, e.g., after a change of train orientation or running direction.
- WordTraceId: 51911
- atomic: true
- Legal Obligation: mandatory
- implement: true
- implementerEnhanced: It shall be possible for the
  RBC
  [EXTERNAL]
  to shift the location reference,
  e.g.
  [WEAK]
  ,
  after
  [TIME]
  a change of train orientation or running direction.
- kind: ordinary

###### 3.6.3.2.5.1 (Requirement Type)
Justification: Refer to Figure 13. To make it possible to shift the location reference if – due to the location of the LRBG and the start location – distance (1) would become a negative value.
- WordTraceId: 52041
- atomic: false
- Legal Obligation: not applicable
- implement: false
- implementerEnhanced: Justification: Refer to Figure 13. To make it possible to shift the location reference
  if
  [CONDITION]
  – due to the location of the
  LRBG
  [EXTERNAL]
  and the start location – distance (1) would become a negative value.
- kind: Justification
- CrossRefLink -> 3.6.3.2.5.1[2].[f]13.C

###### 3.6.3.2.5.1[2] (Requirement Type)
- WordTraceId: 52276
- atomic: false
- Legal Obligation: not applicable
- implement: false
- kind: Placeholder

###### 3.6.3.2.5.1[2].[f]13 (Requirement Type)
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- WordTraceId: 52304
- atomic: false
- Legal Obligation: not applicable
- implement: false
- kind: Figure

###### 3.6.3.2.5.1[2].[f]13.C (Requirement Type)
Figure {Figure 13}: Shifted Location Reference (shown for continuous data /location profile, but also valid for non continuous data profile).
- WordTraceId: 52304
- atomic: true
- Legal Obligation: unknown
- PlainText: Figure 13: Shifted Location Reference (shown for continuous data /location profile, but also valid for non continuous data profile).
- implement: false
- kind: Figure

###### 3.6.3.2.6 (Requirement Type)
With regards to Figure 12 the following applies to linking information
- WordTraceId: 52462
- atomic: true
- Legal Obligation: unknown
- implement: false
- kind: Heading
- CrossRefLink -> 3.6.3.2.1[2].[f]12.C

###### 3.6.3.2.6.a (Requirement Type)
The distance (1) shall be given to the first balise group included in the linking information
- WordTraceId: 52560
- atomic: true
- Legal Obligation: mandatory
- implement: true
- implementerEnhanced: The distance (1) shall be given to the first
  balise group
  [EXTERNAL]
  included in the linking information
- ListNumberText: a)
- kind: ordinary

###### 3.6.3.2.6.b (Requirement Type)
The distance (n) shall be given as the distance between two consecutive balise groups
- WordTraceId: 52654
- atomic: true
- Legal Obligation: mandatory
- implement: true
- implementerEnhanced: The distance (n) shall be given as the distance between two consecutive
  balise groups
  [EXTERNAL]
- ListNumberText: b)
- kind: ordinary

###### 3.6.3.2.6.c (Requirement Type)
Each value (n) shall represent the linking information related to that balise group.
- WordTraceId: 52741
- atomic: true
- Legal Obligation: mandatory
- implement: true
- implementerEnhanced: Each value (n) shall represent the linking information related to that
  balise group
  [EXTERNAL]
  .
- ListNumberText: c)
- kind: ordinary

#### 3.6.4 (Requirement Type)
Train Position Confidence Interval and Relocation
- WordTraceId: 52826
- atomic: false
- Legal Obligation: not applicable
- implement: false
- kind: Heading

##### 3.6.4.1 (Requirement Type)
All location related information transmitted from trackside equipment shall be used by the on-board equipment taking into account the confidence interval to the train position, if required for safe operation.
- WordTraceId: 52876
- atomic: true
- Legal Obligation: mandatory
- implement: true
- implementerEnhanced: All location related information transmitted from
  trackside
  [EXTERNAL]
  equipment shall be used by the
  on-board equipment
  [SELF]
  taking into account the confidence interval to the train position,
  if
  [CONDITION]
  required for safe operation.
- kind: ordinary

##### 3.6.4.2 (Requirement Type)
The confidence interval to the train position shall refer to the distance to the LRBG and shall take into account
- WordTraceId: 53085
- atomic: false
- Legal Obligation: mandatory
- implement: true
- implementerEnhanced: The confidence interval to the train position shall refer to the distance to the
  LRBG
  [EXTERNAL]
  and shall take into account
- kind: ordinary

###### 3.6.4.2.a (Requirement Type)
On-board over-reading amount and under-reading amount (odometer accuracy plus the error in detection of the balise group location reference)
- WordTraceId: 53199
- atomic: true
- Legal Obligation: unknown
- implement: true
- implementerEnhanced: On-board over-reading amount and under-reading amount (odometer accuracy plus the error in detection of the
  balise group
  [EXTERNAL]
  location reference)
- ListNumberText: a)
- kind: ordinary

###### 3.6.4.2.b (Requirement Type)
The location accuracy of the LRBG.
- WordTraceId: 53340
- atomic: true
- Legal Obligation: unknown
- implement: true
- implementerEnhanced: The location accuracy of the
  LRBG
  [EXTERNAL]
  .
- ListNumberText: b)
- kind: ordinary

###### 3.6.4.2.1 (Requirement Type)
Distance information received from trackside shall be evaluated on-board as nominal information (without taking into account any tolerances).
- WordTraceId: 53375
- atomic: true
- Legal Obligation: mandatory
- implement: true
- implementerEnhanced: Distance information received from
  trackside
  [EXTERNAL]
  shall be evaluated on-board as nominal information (without taking into account any tolerances).
- kind: ordinary

###### 3.6.4.2.2 (Requirement Type)
Note: The confidence interval increases in relation to the distance travelled from the LRBG depending on the accuracy of odometer equipment until it is reset when another balise group becomes the LRBG.
- WordTraceId: 53517
- atomic: false
- Legal Obligation: not applicable
- implement: false
- implementerEnhanced: Note: The confidence interval increases in relation to the distance travelled from the
  LRBG
  [EXTERNAL]
  depending on the accuracy of odometer equipment
  until
  [TIME]
  it is reset
  when
  [CONDITION]
  another
  balise group
  [EXTERNAL]
  becomes the
  LRBG
  [EXTERNAL]
  .
- kind: Note

###### 3.6.4.2.3 (Requirement Type)
The value of the Location Accuracy shall be determined by Linking information if available, if not, by the corresponding National Value, or the corresponding Default Value if the National Value is not applicable.
- WordTraceId: 53719
- atomic: true
- Legal Obligation: mandatory
- implement: true
- implementerEnhanced: The value of the Location Accuracy shall be determined by Linking information
  if
  [CONDITION]
  available,
  if
  [CONDITION]
  not, by the corresponding National Value, or the corresponding Default Value
  if
  [CONDITION]
  the National Value is not applicable.
- kind: ordinary

##### 3.6.4.3 (Requirement Type)
When another balise group becomes the LRBG or when evaluating (see section 4.8) location related trackside information, which is referred to a previously received balise group different from the LRBG, all the location related information shall be relocated by subtracting from the distances that are counted from the reference balise group of the location related information:
- WordTraceId: 53932
- atomic: true
- Legal Obligation: mandatory
- implement: true
- implementerEnhanced: When
  [CONDITION]
  another
  balise group
  [EXTERNAL]
  becomes the
  LRBG
  [EXTERNAL]
  or
  when
  [CONDITION]
  evaluating (see section 4.8) location related
  trackside
  [EXTERNAL]
  information, which is referred to a previously received
  balise group
  [EXTERNAL]
  different from the
  LRBG
  [EXTERNAL]
  , all the location related information shall be relocated by subtracting from the distances that are counted from the reference
  balise group
  [EXTERNAL]
  of the location related information:
- kind: ordinary
- CrossRefLink -> 4.8

###### 3.6.4.3.a (Requirement Type)
the distance between the reference balise group of the location related information and the LRBG, retrieved from linking information if it is available and it includes both the reference balise group and the LRBG, OR
- WordTraceId: 54310
- atomic: true
- Legal Obligation: unknown
- implement: true
- implementerEnhanced: the distance between the reference
  balise group
  [EXTERNAL]
  of the location related information and the
  LRBG
  [EXTERNAL]
  , retrieved from linking information
  if
  [CONDITION]
  it is available and it includes both the reference
  balise group
  [EXTERNAL]
  and the
  LRBG
  [EXTERNAL]
  , OR
- ListNumberText: a)
- kind: ordinary

###### 3.6.4.3.b (Requirement Type)
in all other cases, the estimated travelled distance between the reference balise group of the location related information and the LRBG.
- WordTraceId: 54527
- atomic: true
- Legal Obligation: unknown
- implement: true
- implementerEnhanced: in all other cases, the estimated travelled distance between the reference
  balise group
  [EXTERNAL]
  of the location related information and the
  LRBG
  [EXTERNAL]
  .
- ListNumberText: b)
- kind: ordinary

###### 3.6.4.3.1 (Requirement Type)
Justification: it is always the trackside responsibility to provide linking in due course, knowing this rule; if the location related information is to be used in situations where linking is not provided (e.g. TSR transmitted by balise group marked as unlinked), the trackside can include provisions, if deemed necessary, when engineering the distance information.
- WordTraceId: 54665
- atomic: false
- Legal Obligation: not applicable
- implement: false
- implementerEnhanced: Justification: it is always the
  trackside
  [EXTERNAL]
  responsibility to provide linking in due course, knowing this rule;
  if
  [CONDITION]
  the location related information is to be used in situations where linking is not provided (
  e.g.
  [WEAK]
  TSR transmitted by
  balise group
  [EXTERNAL]
  marked as unlinked), the
  trackside
  [EXTERNAL]
  can include provisions,
  if
  [CONDITION]
  deemed necessary,
  when
  [CONDITION]
  engineering the distance information.
- kind: Justification

###### 3.6.4.3.1[2] (Requirement Type)
- WordTraceId: 55030
- atomic: false
- Legal Obligation: not applicable
- implement: false
- kind: Placeholder

###### 3.6.4.3.1[2].[f]13a (Requirement Type)
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- WordTraceId: 55058
- atomic: false
- Legal Obligation: not applicable
- implement: false
- kind: Figure

###### 3.6.4.3.1[2].[f]13a.C (Requirement Type)
Figure 13a:
Reset of confidence interval and relocation, on change of LRBG
- WordTraceId: 55058
- atomic: true
- Legal Obligation: unknown
- implement: false
- implementerEnhanced: Figure 13a: Reset of confidence interval and relocation, on change of
  LRBG
  [EXTERNAL]
- kind: Figure

###### 3.6.4.3.1[3] (Requirement Type)
- WordTraceId: 55134
- atomic: false
- Legal Obligation: not applicable
- implement: false
- kind: Placeholder

###### 3.6.4.3.1[3].[f]13b (Requirement Type)
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- WordTraceId: 55162
- atomic: false
- Legal Obligation: not applicable
- implement: false
- kind: Figure

###### 3.6.4.3.1[3].[f]13b.C (Requirement Type)
Figure 13b: Relocation of trackside information referred to previously passed balise group, different from the current LRBG
- WordTraceId: 55162
- atomic: true
- Legal Obligation: unknown
- implement: false
- implementerEnhanced: Figure 13b: Relocation of
  trackside
  [EXTERNAL]
  information referred to previously passed
  balise group
  [EXTERNAL]
  , different from the current
  LRBG
  [EXTERNAL]
- kind: Figure

##### 3.6.4.4 (Requirement Type)
The train front end position shall be identified in the following way
- WordTraceId: 55286
- atomic: true
- Legal Obligation: not applicable
- implement: false
- kind: Heading

###### 3.6.4.4.a (Requirement Type)
The estimated front end position.
- WordTraceId: 55356
- atomic: true
- Legal Obligation: mandatory
- implement: true
- ListNumberText: a)
- kind: ordinary

###### 3.6.4.4.b (Requirement Type)
The max(imum) safe front end position, differing from the estimated position by the under-reading amount in the distance measured from the LRBG plus the location accuracy of the LRBG.
I.e. in relation to the orientation of the train this position is in advance of the estimated position.
- WordTraceId: 55390
- atomic: true
- Legal Obligation: mandatory
- implement: true
- implementerEnhanced: The max(imum) safe front end position, differing from the estimated position by the under-reading amount in the distance measured from the
  LRBG
  [EXTERNAL]
  plus the location accuracy of the
  LRBG
  [EXTERNAL]
  . I.e. in relation to the orientation of the train this position is in advance of the estimated position.
- ListNumberText: b)
- kind: ordinary

###### 3.6.4.4.c (Requirement Type)
The min(imum) safe front end position, differing from the estimated position by the over-reading amount in the distance measured from the LRBG plus the location accuracy of the LRBG.
I.e. in relation to the orientation of the train this position is in rear of the estimated position.
- WordTraceId: 55680
- atomic: false
- Legal Obligation: mandatory
- implement: true
- implementerEnhanced: The min(imum) safe front end position, differing from the estimated position by the over-reading amount in the distance measured from the
  LRBG
  [EXTERNAL]
  plus the location accuracy of the
  LRBG
  [EXTERNAL]
  . I.e. in relation to the orientation of the train this position is in rear of the estimated position.
- ListNumberText: c)
- kind: ordinary

###### 3.6.4.4.1 (Requirement Type)
Note: The rear end position is referenced in the same way. However min safe rear end is only safe if sent together with train integrity information.
- WordTraceId: 55965
- atomic: false
- Legal Obligation: mandatory
- implement: false
- implementerEnhanced: Note: The rear end position is referenced in the same way. However min safe rear end is only safe
  if
  [CONDITION]
  sent together with train integrity information.
- kind: Note

###### 3.6.4.4.1[2] (Requirement Type)
- WordTraceId: 56114
- atomic: false
- Legal Obligation: not applicable
- implement: false
- kind: Placeholder

###### 3.6.4.4.1[2].[f]13c (Requirement Type)
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- WordTraceId: 56116
- atomic: false
- Legal Obligation: mandatory
- implement: false
- kind: Figure

###### 3.6.4.4.1[2].[f]13c.C (Requirement Type)
Figure 13c: Train confidence interval and train front end position
- WordTraceId: 56116
- atomic: true
- Legal Obligation: mandatory
- implement: false
- kind: Figure

##### 3.6.4.5 (Requirement Type)
Intentionally deleted.
- WordTraceId: 56183
- atomic: false
- Legal Obligation: not applicable
- implement: false
- kind: Placeholder

##### 3.6.4.6 (Requirement Type)
The estimated front end shall be used when supervising location information, unless stated otherwise.
- WordTraceId: 56206
- atomic: true
- Legal Obligation: mandatory
- implement: true
- implementerEnhanced: The estimated front end shall be used
  when
  [CONDITION]
  supervising location information, unless stated otherwise.
- kind: ordinary

##### 3.6.4.7 (Requirement Type)
Supervision of location related information transmitted by a balise group marked as unlinked and referred to this balise group:
- WordTraceId: 56308
- atomic: true
- Legal Obligation: unknown
- implement: false
- implementerEnhanced: Supervision of location related information transmitted by a
  balise group
  [EXTERNAL]
  marked as unlinked and referred to this
  balise group
  [EXTERNAL]
  :
- kind: Heading

###### 3.6.4.7.1 (Requirement Type)
By exception to clause 3.6.1.3, the train position is referred to this balise group marked as unlinked. The ERTMS/ETCS on-board equipment shall temporarily apply by analogy clauses 3.6.4.2, 3.6.4.2.1, 3.6.4.2.3 and 3.6.4.4 to determine an additional confidence interval, until a further received balise group becomes the LRBG or the location related information is deleted on-board.
- WordTraceId: 56436
- atomic: false
- Legal Obligation: mandatory
- implement: true
- implementerEnhanced: By exception to clause 3.6.1.3, the train position is referred to this
  balise group
  [EXTERNAL]
  marked as unlinked. The
  ERTMS/ETCS on-board equipment
  [SELF]
  shall
  temporarily
  [WEAK]
  apply by analogy clauses 3.6.4.2, 3.6.4.2.1, 3.6.4.2.3 and 3.6.4.4 to determine an additional confidence interval,
  until
  [TIME]
  a further received
  balise group
  [EXTERNAL]
  becomes the
  LRBG
  [EXTERNAL]
  or the location related information is deleted on-board.
- kind: ordinary
- CrossRefLink -> 3.6.1.3
- CrossRefLink -> 3.6.4.2
- CrossRefLink -> 3.6.4.2.1
- CrossRefLink -> 3.6.4.2.3
- CrossRefLink -> 3.6.4.4

###### 3.6.4.7.2 (Requirement Type)
If another balise group marked as unlinked is received before the additional confidence interval is deleted:
- WordTraceId: 56819
- atomic: true
- Legal Obligation: unknown
- implement: true
- implementerEnhanced: If
  [CONDITION]
  another
  balise group
  [EXTERNAL]
  marked as unlinked is received before the additional confidence interval is deleted:
- kind: ordinary

###### 3.6.4.7.2.a (Requirement Type)
the additional confidence interval shall be reset in relation to this new balise group marked as unlinked
- WordTraceId: 56928
- atomic: true
- Legal Obligation: mandatory
- implement: true
- implementerEnhanced: the additional confidence interval shall be reset in relation to this new
  balise group
  [EXTERNAL]
  marked as unlinked
- ListNumberText: a)
- kind: ordinary

###### 3.6.4.7.2.b (Requirement Type)
the location related information referred to the previous balise group marked as unlinked shall be relocated by subtracting the estimated travelled distance between both balise groups from the distances that are counted from this previous balise group marked as unlinked.
- WordTraceId: 57034
- atomic: true
- Legal Obligation: mandatory
- implement: true
- implementerEnhanced: the location related information referred to the previous
  balise group
  [EXTERNAL]
  marked as unlinked shall be relocated by subtracting the estimated travelled distance between both
  balise groups
  [EXTERNAL]
  from the distances that are counted from this previous
  balise group
  [EXTERNAL]
  marked as unlinked.
- ListNumberText: b)
- kind: ordinary

#### 3.6.5 (Requirement Type)
Position Reporting to the RBC
- WordTraceId: 57306
- atomic: false
- Legal Obligation: not applicable
- implement: false
- implementerEnhanced: Position Reporting to the
  RBC
  [EXTERNAL]
- kind: Heading

##### 3.6.5.1 (Requirement Type)
General
- WordTraceId: 57336
- atomic: false
- Legal Obligation: not applicable
- implement: false
- kind: Heading

###### 3.6.5.1.1 (Requirement Type)
The position shall refer to the front end of the respective engine with regards to the train orientation.
- WordTraceId: 57344
- atomic: true
- Legal Obligation: mandatory
- implement: true
- kind: ordinary

###### 3.6.5.1.1.1 (Requirement Type)
Intentionally deleted.
- WordTraceId: 57450
- atomic: false
- Legal Obligation: not applicable
- implement: false
- kind: Placeholder

###### 3.6.5.1.2 (Requirement Type)
The position report shall contain at least the following position and direction data
- WordTraceId: 57473
- atomic: true
- Legal Obligation: mandatory
- implement: true
- implementerEnhanced: The position report shall contain
  at least
  [WEAK]
  the following position and direction data
- kind: ordinary

###### 3.6.5.1.2.a (Requirement Type)
The distance between the LRBG and the estimated front end of the train.
- WordTraceId: 57558
- atomic: true
- Legal Obligation: mandatory
- implement: true
- implementerEnhanced: The distance between the
  LRBG
  [EXTERNAL]
  and the estimated front end of the train.
- ListNumberText: a)
- kind: ordinary

###### 3.6.5.1.2.b (Requirement Type)
The distance from the estimated front end position to the min safe front end position and the distance from the estimated front end position to the max safe front end position.
- WordTraceId: 57630
- atomic: true
- Legal Obligation: mandatory
- implement: true
- ListNumberText: b)
- kind: ordinary

###### 3.6.5.1.2.c (Requirement Type)
The identity of the location reference, the LRBG.
- WordTraceId: 57807
- atomic: true
- Legal Obligation: mandatory
- implement: true
- implementerEnhanced: The identity of the location reference, the
  LRBG
  [EXTERNAL]
  .
- ListNumberText: c)
- kind: ordinary

###### 3.6.5.1.2.d (Requirement Type)
The orientation of the train in relation to the LRBG orientation.
Note: Driver selected running direction is only handled by the on-board system.
- WordTraceId: 57857
- atomic: false
- Legal Obligation: mandatory
- implement: true
- implementerEnhanced: The orientation of the train in relation to the
  LRBG
  [EXTERNAL]
  orientation. Note:
  Driver
  [EXTERNAL]
  selected running direction is only handled by the on-board system.
- ListNumberText: d)
- kind: ordinary

###### 3.6.5.1.2.e (Requirement Type)
The position of the front end of the train in relation to the LRBG (nominal or reverse side of the LRBG).
- WordTraceId: 58003
- atomic: true
- Legal Obligation: mandatory
- implement: true
- implementerEnhanced: The position of the front end of the train in relation to the
  LRBG
  [EXTERNAL]
  (nominal or reverse side of the
  LRBG
  [EXTERNAL]
  ).
- ListNumberText: e)
- kind: ordinary

###### 3.6.5.1.2.f (Requirement Type)
The estimated speed
- WordTraceId: 58109
- atomic: true
- Legal Obligation: mandatory
- implement: true
- ListNumberText: f)
- kind: ordinary

###### 3.6.5.1.2.g (Requirement Type)
Train integrity information.
- WordTraceId: 58129
- atomic: true
- Legal Obligation: mandatory
- implement: true
- ListNumberText: g)
- kind: ordinary

###### 3.6.5.1.2.h (Requirement Type)
Direction of train movement in relation to the LRBG orientation
- WordTraceId: 58158
- atomic: true
- Legal Obligation: mandatory
- implement: true
- implementerEnhanced: Direction of train movement in relation to the
  LRBG
  [EXTERNAL]
  orientation
- ListNumberText: h)
- kind: ordinary

###### 3.6.5.1.2.i (Requirement Type)
Optionally, the previous LRBG (see 3.4.2.3.3).
- WordTraceId: 58222
- atomic: true
- Legal Obligation: mandatory
- implement: true
- implementerEnhanced: Optionally, the
  previous
  LRBG
  [EXTERNAL]
  [LINKED_PHRASE]
  (see 3.4.2.3.3).
- ListNumberText: i)
- kind: ordinary
- CrossRefLink -> 3.4.2.3.3
- KnownTermLink -> 3.4.2.3.3.1

###### 3.6.5.1.2[2] (Requirement Type)
- WordTraceId: 58269
- atomic: false
- Legal Obligation: not applicable
- implement: false
- kind: Placeholder

###### 3.6.5.1.2[2].[f]14 (Requirement Type)
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- WordTraceId: 58318
- atomic: false
- Legal Obligation: not applicable
- implement: false
- kind: Figure

###### 3.6.5.1.2[2].[f]14.C (Requirement Type)
Figure {Figure 14}: Information given in a position report (two examples to show the relation between LRBG and train orientation)
- WordTraceId: 58318
- atomic: true
- Legal Obligation: unknown
- PlainText: Figure 14: Information given in a position report (two examples to show the relation between LRBG and train orientation)
- implement: false
- implementerEnhanced: Figure 14: Information given in a position report (two examples to show the relation between
  LRBG
  [EXTERNAL]
  and train orientation)
- kind: Figure

###### 3.6.5.1.3 (Requirement Type)
Intentionally deleted.
- WordTraceId: 58464
- atomic: false
- Legal Obligation: not applicable
- implement: false
- kind: Placeholder

###### 3.6.5.1.4 (Requirement Type)
The on-board equipment shall send position reports as requested by the RBC in the position report parameters. In addition, it shall also send a position report if at least one of the events listed hereafter occurs:
- WordTraceId: 58487
- atomic: false
- Legal Obligation: mandatory
- implement: true
- implementerEnhanced: The
  on-board equipment
  [SELF]
  shall send position reports as requested by the
  RBC
  [EXTERNAL]
  in the position report parameters. In addition, it shall also send a position report
  if
  [CONDITION]
  at least
  [WEAK]
  one of the events listed
  hereafter
  [WEAK]
  occurs:
- kind: ordinary

###### 3.6.5.1.4.a (Requirement Type)
The train reaches standstill, if applicable to the current mode.
- WordTraceId: 58702
- atomic: true
- Legal Obligation: mandatory (>= 1)
- implement: true
- implementerEnhanced: The train reaches standstill,
  if
  [CONDITION]
  applicable to the current mode.
- ListNumberText: a)
- kind: ordinary

###### 3.6.5.1.4.b (Requirement Type)
The mode changes.
- WordTraceId: 58767
- atomic: true
- Legal Obligation: mandatory (>= 1)
- implement: true
- ListNumberText: b)
- kind: ordinary

###### 3.6.5.1.4.c (Requirement Type)
The driver confirms train integrity.
- WordTraceId: 58785
- atomic: true
- Legal Obligation: mandatory (>= 1)
- implement: true
- implementerEnhanced: The
  driver
  [EXTERNAL]
  confirms train integrity.
- ListNumberText: c)
- kind: ordinary

###### 3.6.5.1.4.d (Requirement Type)
A loss of train integrity is detected.
- WordTraceId: 58822
- atomic: true
- Legal Obligation: mandatory (>= 1)
- implement: true
- ListNumberText: d)
- kind: ordinary

###### 3.6.5.1.4.e (Requirement Type)
The train passes a RBC/RBC border with its min safe rear end.
- WordTraceId: 58861
- atomic: true
- Legal Obligation: mandatory (>= 1)
- implement: true
- implementerEnhanced: The train passes a
  RBC
  [EXTERNAL]
  /
  RBC
  [EXTERNAL]
  border with its min safe rear end.
- ListNumberText: e)
- kind: ordinary

###### 3.6.5.1.4.f (Requirement Type)
The train passes a level transition border (from level 2/3 to level 0, NTC, 1) with its min safe rear end.
- WordTraceId: 58923
- atomic: true
- Legal Obligation: mandatory (>= 1)
- implement: true
- ListNumberText: f)
- kind: ordinary

###### 3.6.5.1.4.g (Requirement Type)
The level changes.
- WordTraceId: 59030
- atomic: true
- Legal Obligation: mandatory (>= 1)
- implement: true
- ListNumberText: g)
- kind: ordinary

###### 3.6.5.1.4.h (Requirement Type)
A communication session is successfully established.
- WordTraceId: 59049
- atomic: true
- Legal Obligation: mandatory (>= 1)
- implement: true
- ListNumberText: h)
- kind: ordinary

###### 3.6.5.1.4.i (Requirement Type)
Intentionally moved.
- WordTraceId: 59102
- atomic: false
- Legal Obligation: not applicable
- implement: false
- ListNumberText: i)
- kind: Placeholder

###### 3.6.5.1.4.j (Requirement Type)
The train passes an LRBG compliant balise group (see 3.6.2.2.2), if no position report parameters are stored on-board.
- WordTraceId: 59123
- atomic: true
- Legal Obligation: mandatory (>= 1)
- implement: true
- implementerEnhanced: The train passes an
  LRBG
  [EXTERNAL]
  compliant
  balise group
  [EXTERNAL]
  (see 3.6.2.2.2),
  if
  [CONDITION]
  no position report parameters are stored on-board.
- ListNumberText: j)
- kind: ordinary
- CrossRefLink -> 3.6.2.2.2

###### 3.6.5.1.4.k (Requirement Type)
The train passes a RBC/RBC border with its max safe front end.
- WordTraceId: 59242
- atomic: true
- Legal Obligation: mandatory (>= 1)
- implement: true
- implementerEnhanced: The train passes a
  RBC
  [EXTERNAL]
  /
  RBC
  [EXTERNAL]
  border with its max safe front end.
- ListNumberText: k)
- kind: ordinary

###### 3.6.5.1.4.1 (Requirement Type)
If the position report results from one or more events listed in 3.6.5.1.4, its content shall reflect the consequences of these events.
- WordTraceId: 59305
- atomic: true
- Legal Obligation: mandatory (>= 1)
- implement: true
- implementerEnhanced: If
  [CONDITION]
  the position report results from one or more events listed in 3.6.5.1.4, its content shall reflect the consequences of these events.
- kind: ordinary
- CrossRefLink -> 3.6.5.1.4

###### 3.6.5.1.5 (Requirement Type)
For the position report parameters requested by the RBC the following possibilities shall be available, individually or in combination
- WordTraceId: 59441
- atomic: true
- Legal Obligation: mandatory
- implement: true
- implementerEnhanced: For the position report parameters requested by the
  RBC
  [EXTERNAL]
  the following possibilities shall be available, individually or in combination
- kind: ordinary

###### 3.6.5.1.5.a (Requirement Type)
Periodically in time.
- WordTraceId: 59576
- atomic: true
- Legal Obligation: mandatory
- implement: true
- implementerEnhanced: Periodically in
  time
  [TIME]
  .
- ListNumberText: a)
- kind: ordinary

###### 3.6.5.1.5.b (Requirement Type)
Periodically in space.
- WordTraceId: 59598
- atomic: true
- Legal Obligation: mandatory
- implement: true
- ListNumberText: b)
- kind: ordinary

###### 3.6.5.1.5.c (Requirement Type)
When the max safe front end or min safe rear end of the train has passed a specified location.
- WordTraceId: 59621
- atomic: true
- Legal Obligation: mandatory
- implement: true
- implementerEnhanced: When
  [CONDITION]
  the max safe front end or min safe rear end of the train has passed a specified location.
- ListNumberText: c)
- kind: ordinary

###### 3.6.5.1.5.d (Requirement Type)
At every passage of an LRBG compliant balise group (see 3.6.2.2.2).
- WordTraceId: 59716
- atomic: true
- Legal Obligation: mandatory
- implement: true
- implementerEnhanced: At every passage of an
  LRBG
  [EXTERNAL]
  compliant
  balise group
  [EXTERNAL]
  (see 3.6.2.2.2).
- ListNumberText: d)
- kind: ordinary
- CrossRefLink -> 3.6.2.2.2

###### 3.6.5.1.5.e (Requirement Type)
Immediately.
- WordTraceId: 59784
- atomic: true
- Legal Obligation: mandatory
- implement: true
- implementerEnhanced: Immediately
  [WEAK]
  .
- ListNumberText: e)
- kind: ordinary

###### 3.6.5.1.5.1 (Requirement Type)
Note: d) and e) can not be combined.
- WordTraceId: 59797
- atomic: false
- Legal Obligation: mandatory
- implement: false
- kind: Note

###### 3.6.5.1.6 (Requirement Type)
Deleted.
- WordTraceId: 59834
- atomic: false
- Legal Obligation: not applicable
- implement: false
- kind: Placeholder

###### 3.6.5.1.7 (Requirement Type)
The given position report parameters shall be valid until new parameters are given from the RBC.
- WordTraceId: 59843
- atomic: true
- Legal Obligation: mandatory
- implement: true
- implementerEnhanced: The given position report parameters shall be valid
  until
  [TIME]
  new parameters are given from the
  RBC
  [EXTERNAL]
  .
- kind: ordinary

###### 3.6.5.1.8 (Requirement Type)
The mode and level reported in a position report shall be consistent (e.g., no mode that relates to the previous level).
- WordTraceId: 59940
- atomic: true
- Legal Obligation: mandatory
- implement: true
- implementerEnhanced: The mode and level reported in a position report shall be consistent (
  e.g.
  [WEAK]
  , no mode that relates to the previous level).
- kind: ordinary

##### 3.6.5.2 (Requirement Type)
Report of Train Rear End Position for Level 3
- WordTraceId: 60061
- atomic: false
- Legal Obligation: not applicable
- implement: false
- kind: Heading

###### 3.6.5.2.1 (Requirement Type)
Train integrity information shall be given by external device or by driver.
- WordTraceId: 60107
- atomic: true
- Legal Obligation: mandatory
- implement: true
- implementerEnhanced: Train integrity information shall be given by
  external device
  [EXTERNAL]
  or by
  driver
  [EXTERNAL]
  .
- kind: ordinary

###### 3.6.5.2.2 (Requirement Type)
Driver input of train integrity shall only be permitted at standstill.
- WordTraceId: 60183
- atomic: true
- Legal Obligation: mandatory
- implement: true
- implementerEnhanced: Driver
  [EXTERNAL]
  input of train integrity shall only be permitted at standstill.
- kind: ordinary

###### 3.6.5.2.3 (Requirement Type)
The train integrity information shall consist of
- WordTraceId: 60254
- atomic: true
- Legal Obligation: mandatory
- implement: true
- kind: ordinary

###### 3.6.5.2.3.a (Requirement Type)
Train integrity status information
- WordTraceId: 60303
- atomic: true
- Legal Obligation: unknown
- implement: true
- ListNumberText: a)
- kind: ordinary

###### 3.6.5.2.3.a.*[1] (Requirement Type)
No train integrity information
- WordTraceId: 60338
- atomic: true
- Legal Obligation: unknown
- implement: true
- ListNumberText: ·
- kind: ordinary

###### 3.6.5.2.3.a.*[2] (Requirement Type)
Train integrity information confirmed by integrity monitoring device
- WordTraceId: 60369
- atomic: true
- Legal Obligation: unknown
- implement: true
- ListNumberText: ·
- kind: ordinary

###### 3.6.5.2.3.a.*[3] (Requirement Type)
Train integrity information confirmed (entered) by driver
- WordTraceId: 60439
- atomic: true
- Legal Obligation: unknown
- implement: true
- implementerEnhanced: Train integrity information confirmed (entered) by
  driver
  [EXTERNAL]
- ListNumberText: ·
- kind: ordinary

###### 3.6.5.2.3.a.*[4] (Requirement Type)
Train integrity lost
- WordTraceId: 60497
- atomic: true
- Legal Obligation: unknown
- implement: true
- ListNumberText: ·
- kind: ordinary

###### 3.6.5.2.3.b (Requirement Type)
Safe train length information (only valid if train integrity is confirmed at the same time).
- WordTraceId: 60518
- atomic: true
- Legal Obligation: unknown
- implement: true
- implementerEnhanced: Safe train length information (only valid
  if
  [CONDITION]
  train integrity is confirmed at the same
  time
  [TIME]
  ).
- ListNumberText: b)
- kind: ordinary

###### 3.6.5.2.4 (Requirement Type)
The safe train length information shall represent the distance between the min safe rear end (by subtracting the train length from the min. safe front end position at the time when integrity was established last time) and the estimated position of the train front.
- WordTraceId: 60611
- atomic: true
- Legal Obligation: mandatory
- implement: true
- implementerEnhanced: The safe train length information shall represent the distance between the min safe rear end (by subtracting the train length from the min. safe front end position at the
  time
  [TIME]
  when
  [CONDITION]
  integrity was established last
  time
  [TIME]
  ) and the estimated position of the train front.
- kind: ordinary

###### 3.6.5.2.5 (Requirement Type)
The safe train length information shall be re-calculated for every position report using the same last value of min safe rear end position until a new min safe rear end position is established on-board taking into account the time to detect train integrity.
- WordTraceId: 60876
- atomic: true
- Legal Obligation: mandatory
- implement: true
- implementerEnhanced: The safe train length information shall be
  re-calculated
  [AGAIN]
  for every
  [LOOP]
  position report using the same last value of min safe rear end position
  until
  [TIME]
  a new min safe rear end position is established on-board taking into account the
  time
  [TIME]
  to detect train integrity.
- kind: ordinary

###### 3.6.5.2.5[2] (Requirement Type)
- WordTraceId: 61135
- atomic: false
- Legal Obligation: not applicable
- implement: false
- kind: Placeholder

###### 3.6.5.2.5[2].[f]15 (Requirement Type)
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- WordTraceId: 61160
- atomic: false
- Legal Obligation: not applicable
- implement: false
- kind: Figure

###### 3.6.5.2.5[2].[f]15.C (Requirement Type)
Figure {Figure 15}: Calculation of Safe Train Length when train integrity was established
- WordTraceId: 61160
- atomic: true
- Legal Obligation: unknown
- PlainText: Figure 15: Calculation of Safe Train Length when train integrity was established
- implement: false
- implementerEnhanced: Figure 15: Calculation of Safe Train Length
  when
  [CONDITION]
  train integrity was established
- kind: Figure

#### 3.6.6 (Requirement Type)
Geographical position reporting
- WordTraceId: 61268
- atomic: false
- Legal Obligation: not applicable
- implement: false
- kind: Heading

##### 3.6.6.1 (Requirement Type)
The ERTMS/ETCS on-board equipment shall display, only on driver request, the geographical position of the estimated front end of the train in relation to the track kilometre. The display of the geographical position shall also be stopped on driver request.
- WordTraceId: 61300
- atomic: false
- Legal Obligation: mandatory
- implement: true
- implementerEnhanced: The
  ERTMS/ETCS on-board equipment
  [SELF]
  shall display, only on
  driver
  [EXTERNAL]
  request, the geographical position of the estimated front end of the train in relation to the track kilometre. The display of the geographical position shall also be stopped on
  driver
  [EXTERNAL]
  request.
- kind: ordinary

##### 3.6.6.2 (Requirement Type)
The resolution of the position indication shall be 1 metre (sufficient to allow the driver to report the train position when communicating with the signalman).
- WordTraceId: 61558
- atomic: true
- Legal Obligation: mandatory
- implement: true
- implementerEnhanced: The resolution of the position indication shall be 1 metre (sufficient to allow the
  driver
  [EXTERNAL]
  to report the train position
  when
  [CONDITION]
  communicating with the
  signalman
  [EXTERNAL]
  ).
- kind: ordinary

##### 3.6.6.3 (Requirement Type)
When receiving new geographical position information (from radio or from balise group), the ERTMS/ETCS on-board equipment shall replace the currently stored geographical position information (if any) by this new received one, continuing the on-going geographical position calculation until at least one of the condition of 3.6.6.9 applies.
- WordTraceId: 61720
- atomic: true
- Legal Obligation: mandatory
- implement: true
- implementerEnhanced: When
  [CONDITION]
  receiving new geographical position information (from radio or from
  balise group
  [EXTERNAL]
  ), the
  ERTMS/ETCS on-board equipment
  [SELF]
  shall replace the currently stored geographical position information (
  if
  [CONDITION]
  any) by this new received one, continuing the on-going geographical position calculation
  until
  [TIME]
  at least
  [WEAK]
  one of the condition of 3.6.6.9 applies.
- kind: ordinary
- CrossRefLink -> 3.6.6.9

##### 3.6.6.4 (Requirement Type)
Geographical position information shall always use a balise group as geographical position reference balise group and if needed an offset from that balise group. A geographical position reference balise group shall be either:
- WordTraceId: 62060
- atomic: false
- Legal Obligation: mandatory
- implement: true
- implementerEnhanced: Geographical position information shall always use a
  balise group
  [EXTERNAL]
  as geographical position reference
  balise group
  [EXTERNAL]
  and
  if
  [CONDITION]
  needed
  [WEAK]
  an offset from that
  balise group
  [EXTERNAL]
  . A geographical position reference
  balise group
  [EXTERNAL]
  shall be either:
- kind: ordinary

###### 3.6.6.4.a (Requirement Type)
part of the last reported balise groups memorised on-board, in case the information is received from radio, OR
- WordTraceId: 62286
- atomic: true
- Legal Obligation: mandatory (== 1)
- implement: true
- implementerEnhanced: part of the last reported
  balise groups
  [EXTERNAL]
  memorised on-board,
  in case
  [CONDITION]
  the information is received from radio, OR
- ListNumberText: a)
- kind: ordinary

###### 3.6.6.4.b (Requirement Type)
the balise group transmitting the information, in case the information is received from balise group, OR
- WordTraceId: 62397
- atomic: true
- Legal Obligation: mandatory (== 1)
- implement: true
- implementerEnhanced: the
  balise group
  [EXTERNAL]
  transmitting the information,
  in case
  [CONDITION]
  the information is received from
  balise group
  [EXTERNAL]
  , OR
- ListNumberText: b)
- kind: ordinary

###### 3.6.6.4.c (Requirement Type)
any balise group not yet passed at the time of reception of the information.
- WordTraceId: 62502
- atomic: true
- Legal Obligation: mandatory (== 1)
- implement: true
- implementerEnhanced: any
  balise group
  [EXTERNAL]
  not yet
  [TIME]
  passed at the
  time
  [TIME]
  of reception of the information.
- ListNumberText: c)
- kind: ordinary

###### 3.6.6.4.1 (Requirement Type)
In case the information is received by radio and at least one of the announced geographical position reference balise group(s) is part of the last reported balise groups memorised on-board, the on-board equipment shall use the data related to the most recently reported balise group.
- WordTraceId: 62579
- atomic: true
- Legal Obligation: mandatory (== 1)
- implement: true
- implementerEnhanced: In case
  [CONDITION]
  the information is received by radio and
  at least
  [WEAK]
  one of the announced geographical position reference
  balise group(s)
  [EXTERNAL]
  is part of the last reported
  balise groups
  [EXTERNAL]
  memorised on-board, the
  on-board equipment
  [SELF]
  shall use the data related to the most recently reported
  balise group
  [EXTERNAL]
  .
- kind: ordinary

###### 3.6.6.4.2 (Requirement Type)
From the currently stored geographical position information, the track kilometre reference given for a geographical reference location shall become applicable if the train has detected the related geographical reference balise group and has travelled the offset distance from this reference balise group.
- WordTraceId: 62863
- atomic: true
- Legal Obligation: mandatory (== 1)
- implement: true
- implementerEnhanced: From the currently stored geographical position information, the track kilometre reference given for a geographical reference location shall become applicable
  if
  [CONDITION]
  the train has detected the related geographical reference
  balise group
  [EXTERNAL]
  and has travelled the offset distance from this reference
  balise group
  [EXTERNAL]
  .
- kind: ordinary

###### 3.6.6.4.3 (Requirement Type)
The announced and not applicable geographical references shall be deleted on-board if the train changes orientation.
- WordTraceId: 63168
- atomic: true
- Legal Obligation: mandatory (== 1)
- implement: true
- implementerEnhanced: The announced and not applicable geographical references shall be deleted on-board
  if
  [CONDITION]
  the train changes orientation.
- kind: ordinary

##### 3.6.6.5 (Requirement Type)
The distance travelled from the geographical reference location shall be taken into account when calculating the geographical position.
- WordTraceId: 63285
- atomic: true
- Legal Obligation: mandatory
- implement: true
- implementerEnhanced: The distance travelled from the geographical reference location shall be taken into account
  when
  [CONDITION]
  calculating the geographical position.
- kind: ordinary

##### 3.6.6.6 (Requirement Type)
In cases where the track kilometre is not incremental (jumps, changes in counting direction, scaling error) the reported position might be wrong between the point of irregularity and the next new reference.
- WordTraceId: 63422
- atomic: true
- Legal Obligation: unknown
- implement: true
- kind: ordinary

##### 3.6.6.7 (Requirement Type)
In cases where single balise groups are used as a reference for geographical position information and where no linking information is available (and therefore no orientation can be assigned to the balise group), the on-board equipment shall ignore the geographical position information related to these single balise groups.
- WordTraceId: 63631
- atomic: true
- Legal Obligation: mandatory
- implement: true
- implementerEnhanced: In cases where
  single
  balise groups
  [EXTERNAL]
  [LINKED_PHRASE]
  are used as a reference for geographical position information and where no linking information is available (and therefore no orientation can be assigned to the
  balise group
  [EXTERNAL]
  ), the
  on-board equipment
  [SELF]
  shall ignore the geographical position information related to these
  single
  balise groups
  [EXTERNAL]
  [LINKED_PHRASE]
  .
- kind: ordinary
- KnownTermLink -> 3.4.2.3.1

##### 3.6.6.8 (Requirement Type)
Intentionally deleted.
- WordTraceId: 63956
- atomic: false
- Legal Obligation: not applicable
- implement: false
- kind: Placeholder

##### 3.6.6.9 (Requirement Type)
The on-board equipment shall continue calculating the position from a track kilometre reference (i.e. this track kilometre reference shall remain applicable) until:
- WordTraceId: 63979
- atomic: false
- Legal Obligation: mandatory
- implement: true
- implementerEnhanced: The
  on-board equipment
  [SELF]
  shall continue calculating the position from a track kilometre reference (i.e. this track kilometre reference shall remain applicable)
  until
  [TIME]
  :
- kind: ordinary

###### 3.6.6.9.a (Requirement Type)
a new track kilometre reference becomes applicable, OR
- WordTraceId: 64144
- atomic: true
- Legal Obligation: unknown
- implement: true
- ListNumberText: a)
- kind: ordinary

###### 3.6.6.9.b (Requirement Type)
it is told not to do so, OR
- WordTraceId: 64199
- atomic: true
- Legal Obligation: unknown
- implement: true
- ListNumberText: b)
- kind: ordinary

###### 3.6.6.9.c (Requirement Type)
the calculated geographical position becomes negative, OR
- WordTraceId: 64227
- atomic: true
- Legal Obligation: unknown
- implement: true
- ListNumberText: c)
- kind: ordinary

###### 3.6.6.9.d (Requirement Type)
no more geographical position information is available (e.g., deleted according to conditions in SRS chapter 4)
- WordTraceId: 64285
- atomic: true
- Legal Obligation: unknown
- implement: true
- implementerEnhanced: no more geographical position information is available (
  e.g.
  [WEAK]
  , deleted according to conditions in SRS chapter 4)
- ListNumberText: d)
- kind: ordinary

###### 3.6.6.9.1 (Requirement Type)
Once a track kilometre reference is no longer applicable, it shall be deleted.
- WordTraceId: 64397
- atomic: true
- Legal Obligation: mandatory
- implement: true
- kind: ordinary

##### 3.6.6.10 (Requirement Type)
The following data shall be included in a message for geographical position (for every track kilometre reference):
- WordTraceId: 64476
- atomic: true
- Legal Obligation: not applicable
- implement: false
- implementerEnhanced: The following data shall be included in a message for geographical position (
  for every
  [LOOP]
  track kilometre reference):
- kind: Heading

###### 3.6.6.10.*[1] (Requirement Type)
Identity of the geographical position reference balise group
- WordTraceId: 64593
- atomic: true
- Legal Obligation: mandatory
- implement: true
- implementerEnhanced: Identity of the geographical position reference
  balise group
  [EXTERNAL]
- ListNumberText: ·
- kind: ordinary

###### 3.6.6.10.*[2] (Requirement Type)
Distance from geographical position reference balise group to the track kilometre reference (offset)
- WordTraceId: 64654
- atomic: true
- Legal Obligation: mandatory
- implement: true
- implementerEnhanced: Distance from geographical position reference
  balise group
  [EXTERNAL]
  to the track kilometre reference (offset)
- ListNumberText: ·
- kind: ordinary

###### 3.6.6.10.*[3] (Requirement Type)
Value of the track kilometre reference
- WordTraceId: 64755
- atomic: true
- Legal Obligation: mandatory
- implement: true
- ListNumberText: ·
- kind: ordinary

###### 3.6.6.10.*[4] (Requirement Type)
Counting direction of the track kilometre in relation to the geographical position reference balise group orientation.
- WordTraceId: 64794
- atomic: true
- Legal Obligation: mandatory
- implement: true
- implementerEnhanced: Counting direction of the track kilometre in relation to the geographical position reference
  balise group
  [EXTERNAL]
  orientation.
- ListNumberText: ·
- kind: ordinary

##### 3.6.6.10[2] (Requirement Type)
- WordTraceId: 64913
- atomic: false
- Legal Obligation: not applicable
- implement: false
- kind: Placeholder

###### 3.6.6.10[2].[f]16 (Requirement Type)
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- WordTraceId: 64938
- atomic: false
- Legal Obligation: not applicable
- implement: false
- kind: Figure

###### 3.6.6.10[2].[f]16.C (Requirement Type)
Figure {Figure 16}: Geographical position example
- WordTraceId: 64938
- atomic: true
- Legal Obligation: unknown
- PlainText: Figure 16: Geographical position example
- implement: false
- implementerEnhanced: Figure 16: Geographical position example
- kind: Figure

### 3.7 (Requirement Type)
Completeness of data for safe train movement
- WordTraceId: 65005
- atomic: false
- Legal Obligation: not applicable
- implement: false
- kind: Heading

#### 3.7.1 (Requirement Type)
Completeness of data
- WordTraceId: 65050
- atomic: false
- Legal Obligation: not applicable
- implement: false
- kind: Heading

##### 3.7.1.1 (Requirement Type)
To control the train movement in an ERTMS/ETCS based system the ERTMS/ETCS on-board equipment shall be given information from the trackside system both concerning the route set for the train and the track description for that route. The following information shall be given from the trackside
- WordTraceId: 65072
- atomic: false
- Legal Obligation: not applicable
- implement: false
- implementerEnhanced: To control the train movement in an ERTMS/ETCS based system the
  ERTMS/ETCS on-board equipment
  [SELF]
  shall be given information from the
  trackside
  [EXTERNAL]
  system both concerning the route set for the train and the track description for that route. The following information shall be given from the
  trackside
  [EXTERNAL]
- kind: Heading

###### 3.7.1.1.a (Requirement Type)
Permission and distance to run, the Movement Authority (MA) (see section 3.8)
- WordTraceId: 65365
- atomic: true
- Legal Obligation: mandatory
- implement: true
- ListNumberText: a)
- kind: ordinary
- CrossRefLink -> 3.8

###### 3.7.1.1.b (Requirement Type)
When needed, limitations related to the movement authority, i.e. Mode profile for On Sight, Limited Supervision or Shunting and signalling related speed restriction (see sections 3.12.4 and 3.11.6). Mode profile and Signalling related Speed restriction shall always be sent together with the MA to which the information belongs
- WordTraceId: 65472
- atomic: false
- Legal Obligation: optional
- implement: true
- implementerEnhanced: When
  [CONDITION]
  needed
  [WEAK]
  , limitations related to the movement authority, i.e. Mode profile for On Sight, Limited Supervision or Shunting and signalling related speed restriction (see sections 3.12.4 and 3.11.6). Mode profile and Signalling related Speed restriction shall always be sent together with the MA to which the information belongs
- ListNumberText: b)
- kind: ordinary
- CrossRefLink -> 3.12.4
- CrossRefLink -> 3.11.6

###### 3.7.1.1.c (Requirement Type)
Track description covering as a minimum the whole distance defined by the MA. Track description includes the following information
- WordTraceId: 65858
- atomic: false
- Legal Obligation: mandatory
- implement: true
- ListNumberText: c)
- kind: ordinary

###### 3.7.1.1.c.*[1] (Requirement Type)
The Static Speed Profile (SSP) (see section 3.11.3).
- WordTraceId: 65989
- atomic: true
- Legal Obligation: mandatory
- implement: true
- ListNumberText: ·
- kind: ordinary
- CrossRefLink -> 3.11.3

###### 3.7.1.1.c.*[2] (Requirement Type)
The gradient profile (see section 3.11.12).
- WordTraceId: 66071
- atomic: true
- Legal Obligation: mandatory
- implement: true
- ListNumberText: ·
- kind: ordinary
- CrossRefLink -> 3.11.12

###### 3.7.1.1.c.*[3] (Requirement Type)
Optionally Axle load Speed Profile (ASP) (see section 3.11.4)
- WordTraceId: 66144
- atomic: true
- Legal Obligation: mandatory
- implement: true
- ListNumberText: ·
- kind: ordinary
- CrossRefLink -> 3.11.4

###### 3.7.1.1.c.*[4] (Requirement Type)
Optionally Speed restriction to ensure a given permitted braking distance (see section 3.11.11)
- WordTraceId: 66235
- atomic: true
- Legal Obligation: mandatory
- implement: true
- ListNumberText: ·
- kind: ordinary
- CrossRefLink -> 3.11.11

###### 3.7.1.1.c.*[5] (Requirement Type)
Optionally track conditions (see section 3.12.1).
- WordTraceId: 66331
- atomic: true
- Legal Obligation: mandatory
- implement: true
- ListNumberText: ·
- kind: ordinary
- CrossRefLink -> 3.12.1

###### 3.7.1.1.c.*[6] (Requirement Type)
Optionally route suitability data (see section 3.12.2).
- WordTraceId: 66410
- atomic: true
- Legal Obligation: mandatory
- implement: true
- ListNumberText: ·
- kind: ordinary
- CrossRefLink -> 3.12.2

###### 3.7.1.1.c.*[7] (Requirement Type)
Optionally areas where reversing is permitted (see section 3.15.4).
- WordTraceId: 66495
- atomic: true
- Legal Obligation: mandatory
- implement: true
- ListNumberText: ·
- kind: ordinary
- CrossRefLink -> 3.15.4

###### 3.7.1.1.c.*[8] (Requirement Type)
Optionally changed adhesion factor (see section 3.18.4.6).
- WordTraceId: 66592
- atomic: true
- Legal Obligation: mandatory
- implement: true
- ListNumberText: ·
- kind: ordinary
- CrossRefLink -> 3.18.4.6

###### 3.7.1.1.d (Requirement Type)
Linking information when available.
- WordTraceId: 66680
- atomic: true
- Legal Obligation: mandatory
- implement: true
- implementerEnhanced: Linking information
  when
  [CONDITION]
  available.
- ListNumberText: d)
- kind: ordinary

#### 3.7.2 (Requirement Type)
Responsibility for completeness of information
- WordTraceId: 66716
- atomic: false
- Legal Obligation: not applicable
- implement: false
- kind: Heading

##### 3.7.2.1 (Requirement Type)
The Movement Authority (MA) shall be given to the on-board equipment
- WordTraceId: 66763
- atomic: true
- Legal Obligation: mandatory
- implement: true
- implementerEnhanced: The Movement Authority (MA) shall be given to the
  on-board equipment
  [SELF]
- kind: ordinary

###### 3.7.2.1.*[1] (Requirement Type)
Together with the other information ( as listed in section 3.7.1.1 c) and d))
or
- WordTraceId: 66833
- atomic: true
- Legal Obligation: mandatory (>= 1)
- implement: true
- ListNumberText: ·
- kind: ordinary
- CrossRefLink -> 3.7.1.1
- CrossRefLink -> 3.7.1.1.c
- CrossRefLink -> 3.7.1.1.d

###### 3.7.2.1.*[2] (Requirement Type)
Separately, if the other information has already been correctly received by the on-board equipment.
- WordTraceId: 66943
- atomic: true
- Legal Obligation: mandatory (>= 1)
- implement: true
- implementerEnhanced: Separately,
  if
  [CONDITION]
  the other information has already been correctly received by the
  on-board equipment
  [SELF]
  .
- ListNumberText: ·
- kind: ordinary

##### 3.7.2.2 (Requirement Type)
The trackside shall be responsible for that the on-board equipment has received the information valid for the distance covered by the Movement Authority.
- WordTraceId: 67043
- atomic: true
- Legal Obligation: mandatory
- implement: true
- implementerEnhanced: The
  trackside
  [EXTERNAL]
  shall be responsible for that the
  on-board equipment
  [SELF]
  has received the information valid for the distance covered by the Movement Authority.
- kind: ordinary

###### 3.7.2.2.1 (Requirement Type)
In case of LOA, trackside shall be responsible for including any track description beyond the LOA relevant for calculating safe supervision limits.
- WordTraceId: 67197
- atomic: true
- Legal Obligation: mandatory
- implement: true
- implementerEnhanced: In case of
  [CONDITION]
  LOA,
  trackside
  [EXTERNAL]
  shall be responsible for including any track description beyond the LOA relevant for calculating safe supervision limits.
- kind: ordinary

##### 3.7.2.3 (Requirement Type)
The MA and the related mode profile, if any, shall not be accepted by the on-board equipment if the SSP and gradient already available on-board or given together with the MA do not cover the full length of the MA.
- WordTraceId: 67345
- atomic: true
- Legal Obligation: mandatory
- implement: true
- implementerEnhanced: The MA and the related mode profile,
  if
  [CONDITION]
  any, shall not be accepted by the
  on-board equipment
  [SELF]
  if
  [CONDITION]
  the SSP and gradient already available on-board or given together with the MA do not cover the full length of the MA.
- kind: ordinary

###### 3.7.2.3.1 (Requirement Type)
Note: Full length means at least from the estimated front end of the train to the supervised location.
- WordTraceId: 67559
- atomic: false
- Legal Obligation: not applicable
- implement: false
- implementerEnhanced: Note: Full length means
  at least
  [WEAK]
  from the estimated front end of the train to the supervised location.
- kind: Note

##### 3.7.2.4 (Requirement Type)
It shall be the responsibility of the trackside to send additional information when needed. The information referred to is
- WordTraceId: 67662
- atomic: false
- Legal Obligation: mandatory
- implement: true
- implementerEnhanced: It shall be the responsibility of the
  trackside
  [EXTERNAL]
  to send additional information
  when
  [CONDITION]
  needed
  [WEAK]
  . The information referred to is
- kind: ordinary

###### 3.7.2.4.*[1] (Requirement Type)
Emergency messages (from RBC only)
- WordTraceId: 67785
- atomic: true
- Legal Obligation: unknown
- implement: true
- implementerEnhanced: Emergency messages (from
  RBC
  [EXTERNAL]
  only)
- ListNumberText: ·
- kind: ordinary

###### 3.7.2.4.*[2] (Requirement Type)
Request to stop earlier (from RBC only)
- WordTraceId: 67820
- atomic: true
- Legal Obligation: unknown
- implement: true
- implementerEnhanced: Request to stop earlier (from
  RBC
  [EXTERNAL]
  only)
- ListNumberText: ·
- kind: ordinary

###### 3.7.2.4.*[3] (Requirement Type)
Temporary speed restrictions
- WordTraceId: 67860
- atomic: true
- Legal Obligation: unknown
- implement: true
- ListNumberText: ·
- kind: ordinary

###### 3.7.2.4.*[4] (Requirement Type)
National values
- WordTraceId: 67889
- atomic: true
- Legal Obligation: unknown
- implement: true
- ListNumberText: ·
- kind: ordinary

###### 3.7.2.4.*[5] (Requirement Type)
Level transition information
- WordTraceId: 67905
- atomic: true
- Legal Obligation: unknown
- implement: true
- ListNumberText: ·
- kind: ordinary

###### 3.7.2.4.*[6] (Requirement Type)
LX speed restrictions
- WordTraceId: 67934
- atomic: true
- Legal Obligation: unknown
- implement: true
- ListNumberText: ·
- kind: ordinary

###### 3.7.2.4.*[7] (Requirement Type)
Inhibition of revocable TSRs from balises in L2/3 (from RBC only)
- WordTraceId: 67956
- atomic: true
- Legal Obligation: unknown
- implement: true
- implementerEnhanced: Inhibition of revocable TSRs from
  balises
  [EXTERNAL]
  in L2/3 (from
  RBC
  [EXTERNAL]
  only)
- ListNumberText: ·
- kind: ordinary

###### 3.7.2.4.*[8] (Requirement Type)
Virtual Balise Cover orders
- WordTraceId: 68022
- atomic: true
- Legal Obligation: unknown
- implement: true
- implementerEnhanced: Virtual
  Balise
  [EXTERNAL]
  Cover orders
- ListNumberText: ·
- kind: ordinary

#### 3.7.3 (Requirement Type)
Extension, replacement of track description and linking information
- WordTraceId: 68050
- atomic: false
- Legal Obligation: not applicable
- implement: false
- kind: Heading

##### 3.7.3.1 (Requirement Type)
New track description and linking information shall replace (in the ERTMS/ETCS on-board equipment) stored information as detailed below:
- WordTraceId: 68118
- atomic: true
- Legal Obligation: mandatory
- implement: true
- implementerEnhanced: New track description and linking information shall replace (in the
  ERTMS/ETCS on-board equipment
  [SELF]
  ) stored information as detailed
  below
  [WEAK]
  :
- kind: ordinary

###### 3.7.3.1.a (Requirement Type)
New Static Speed Profile information shall replace all stored Static Speed Profile information from the start location of the new information.
- WordTraceId: 68255
- atomic: true
- Legal Obligation: mandatory
- implement: true
- ListNumberText: a)
- kind: ordinary

###### 3.7.3.1.b (Requirement Type)
New Gradient Profile information shall replace all stored Gradient Profile information from the start location of the new information.
- WordTraceId: 68398
- atomic: true
- Legal Obligation: mandatory
- implement: true
- ListNumberText: b)
- kind: ordinary

###### 3.7.3.1.c (Requirement Type)
New Axle Load Speed Profile information shall replace all stored Axle Load Speed Profile information from the start location of the first element of the new information.
- WordTraceId: 68533
- atomic: true
- Legal Obligation: mandatory
- implement: true
- ListNumberText: c)
- kind: ordinary

###### 3.7.3.1.d (Requirement Type)
New Speed Restriction to ensure Permitted Braking Distance information shall replace all stored Speed Restriction to ensure Permitted Braking Distance information from the start location of the first element of the new information.
- WordTraceId: 68703
- atomic: true
- Legal Obligation: mandatory
- implement: true
- ListNumberText: d)
- kind: ordinary

###### 3.7.3.1.e (Requirement Type)
New track condition Change of Traction System information shall replace all stored Change of Traction System information.
- WordTraceId: 68935
- atomic: true
- Legal Obligation: mandatory
- implement: true
- ListNumberText: e)
- kind: ordinary

###### 3.7.3.1.f (Requirement Type)
New track condition Big Metal Masses information shall replace all stored Big Metal Masses information from the start location of the first element of the new information.
- WordTraceId: 69057
- atomic: true
- Legal Obligation: mandatory
- implement: true
- ListNumberText: f)
- kind: ordinary

###### 3.7.3.1.g (Requirement Type)
New track condition information of at least one of the types listed here, i.e., sound horn, non stopping area, tunnel stopping area, powerless section - lower pantograph, powerless section - switch off the main power switch, radio hole, air tightness, switch off regenerative brake, switch off eddy current brake for service brake, switch off eddy current brake for emergency brake, switch off magnetic shoe brake, shall replace all stored track condition information of the listed types from the start location of the first element of the new information.
- WordTraceId: 69229
- atomic: true
- Legal Obligation: mandatory
- implement: true
- implementerEnhanced: New track condition information of
  at least
  [WEAK]
  one of the types listed here, i.e., sound horn, non stopping area, tunnel stopping area, powerless section - lower pantograph, powerless section - switch off the main power switch, radio hole, air tightness, switch off regenerative brake, switch off eddy current brake for service brake, switch off eddy current brake for emergency brake, switch off magnetic shoe brake, shall replace all stored track condition information of the listed types from the start location of the first element of the new information.
- ListNumberText: g)
- kind: ordinary

###### 3.7.3.1.h (Requirement Type)
New route suitability loading gauge information shall replace all stored route suitability loading gauge information.
- WordTraceId: 69786
- atomic: true
- Legal Obligation: mandatory
- implement: true
- ListNumberText: h)
- kind: ordinary

###### 3.7.3.1.i (Requirement Type)
New route suitability traction system information shall replace all stored route suitability traction system information.
- WordTraceId: 69904
- atomic: true
- Legal Obligation: mandatory
- implement: true
- ListNumberText: i)
- kind: ordinary

###### 3.7.3.1.j (Requirement Type)
New route suitability axle load information shall replace all stored route suitability axle load information.
- WordTraceId: 70026
- atomic: true
- Legal Obligation: mandatory
- implement: true
- ListNumberText: j)
- kind: ordinary

###### 3.7.3.1.k (Requirement Type)
New reversing area information shall replace all stored reversing area information.
- WordTraceId: 70136
- atomic: true
- Legal Obligation: mandatory
- implement: true
- ListNumberText: k)
- kind: ordinary

###### 3.7.3.1.l (Requirement Type)
New adhesion factor information shall replace all stored adhesion factor information from the start location of the new information.
- WordTraceId: 70220
- atomic: true
- Legal Obligation: mandatory
- implement: true
- ListNumberText: l)
- kind: ordinary

###### 3.7.3.1.m (Requirement Type)
New linking information received as non-infill information shall replace all stored linking information from the LRBG.
- WordTraceId: 70353
- atomic: true
- Legal Obligation: mandatory
- implement: true
- implementerEnhanced: New linking information received as non-infill information shall replace all stored linking information from the
  LRBG
  [EXTERNAL]
  .
- ListNumberText: m)
- kind: ordinary

###### 3.7.3.1.n (Requirement Type)
New linking information received as infill information shall replace all stored linking information from the reference location of the infill information (i.e. the balise group at next main signal).
- WordTraceId: 70472
- atomic: true
- Legal Obligation: mandatory
- implement: true
- implementerEnhanced: New linking information received as infill information shall replace all stored linking information from the reference location of the infill information (i.e. the
  balise group
  [EXTERNAL]
  at next main signal).
- ListNumberText: n)
- kind: ordinary

###### 3.7.3.1.1 (Requirement Type)
Intentionally deleted.
- WordTraceId: 70671
- atomic: false
- Legal Obligation: not applicable
- implement: false
- kind: Placeholder

###### 3.7.3.1.2 (Requirement Type)
Intentionally deleted.
- WordTraceId: 70694
- atomic: false
- Legal Obligation: not applicable
- implement: false
- kind: Placeholder

##### 3.7.3.2 (Requirement Type)
When requested by trackside, the ERTMS/ETCS on-board equipment shall resume initial states beyond a given location individually:
- WordTraceId: 70717
- atomic: true
- Legal Obligation: mandatory
- implement: true
- implementerEnhanced: When
  [CONDITION]
  requested by
  trackside
  [EXTERNAL]
  , the
  ERTMS/ETCS on-board equipment
  [SELF]
  shall resume initial states beyond a given location individually:
- kind: ordinary

###### 3.7.3.2.a (Requirement Type)
for stored Speed Restriction to ensure Permitted Braking Distance information (for initial state, refer to 3.11.11.7)
- WordTraceId: 70846
- atomic: true
- Legal Obligation: unknown
- implement: true
- ListNumberText: a)
- kind: ordinary
- CrossRefLink -> 3.11.11.7

###### 3.7.3.2.b (Requirement Type)
for stored axle load speed profile information (for initial state, refer to 3.11.4.5)
- WordTraceId: 70964
- atomic: true
- Legal Obligation: unknown
- implement: true
- ListNumberText: b)
- kind: ordinary
- CrossRefLink -> 3.11.4.5

###### 3.7.3.2.c (Requirement Type)
through a single request, for all stored track condition information of the following types: sound horn, non stopping area, tunnel stopping area, powerless section – lower pantograph, powerless section – switch off the main power switch, radio hole, air tightness, switch off regenerative brake, switch off eddy current brake for service brake, switch off eddy current brake for emergency brake and switch off magnetic shoe brake (for initial states, refer to 3.12.1.3)
- WordTraceId: 71050
- atomic: true
- Legal Obligation: unknown
- implement: true
- implementerEnhanced: through a single request,
  for all
  [LOOP]
  stored track condition information of the following types: sound horn, non stopping area, tunnel stopping area, powerless section – lower pantograph, powerless section – switch off the main power switch, radio hole, air tightness, switch off regenerative brake, switch off eddy current brake for service brake, switch off eddy current brake for emergency brake and switch off magnetic shoe brake (for initial states, refer to 3.12.1.3)
- ListNumberText: c)
- kind: ordinary
- CrossRefLink -> 3.12.1.3

###### 3.7.3.2.d (Requirement Type)
through a single request, for all stored route suitability information (for initial state, refer to 3.12.2.10).
- WordTraceId: 71520
- atomic: true
- Legal Obligation: unknown
- implement: true
- implementerEnhanced: through a single request,
  for all
  [LOOP]
  stored route suitability information (for initial state, refer to 3.12.2.10).
- ListNumberText: d)
- kind: ordinary
- CrossRefLink -> 3.12.2.10

##### 3.7.3.3 (Requirement Type)
In some situations, the track description and linking information shall be deleted (or initial state shall be resumed) by the on-board equipment.
These various cases where the data is affected (e.g. the MA is shortened) are described in detail in Appendix A3.4.
- WordTraceId: 71632
- atomic: false
- Legal Obligation: mandatory
- implement: true
- implementerEnhanced: In
  some situations
  [WEAK]
  , the track description and linking information shall be deleted (or initial state shall be resumed) by the
  on-board equipment
  [SELF]
  . These various cases where the data is affected (
  e.g.
  [WEAK]
  the MA is shortened) are described in detail in Appendix A3.4.
- kind: ordinary
- CrossRefLink -> A.3.4

##### 3.7.3.4 (Requirement Type)
Intentionally deleted.
- WordTraceId: 71894
- atomic: false
- Legal Obligation: not applicable
- implement: false
- kind: Placeholder

##### 3.7.3.5 (Requirement Type)
Deleted.
- WordTraceId: 71917
- atomic: false
- Legal Obligation: not applicable
- implement: false
- kind: Placeholder

##### 3.7.3.6 (Requirement Type)
Note: regarding the handling of Temporary Speed Restrictions and Level Crossings, see sections 3.11.5 and 3.12.5.
- WordTraceId: 71926
- atomic: false
- Legal Obligation: not applicable
- implement: false
- kind: Note
- CrossRefLink -> 3.11.5
- CrossRefLink -> 3.12.5

### 3.8 (Requirement Type)
Movement authority
- WordTraceId: 72098
- atomic: false
- Legal Obligation: not applicable
- implement: false
- kind: Heading

#### 3.8.1 (Requirement Type)
Characteristics of a MA
- WordTraceId: 72117
- atomic: false
- Legal Obligation: not applicable
- implement: false
- kind: Heading

##### 3.8.1.1 (Requirement Type)
The following characteristics can be used in a Movement Authority (see Figure 17: Structure of an MA):
- WordTraceId: 72142
- atomic: true
- Legal Obligation: unknown
- implement: true
- kind: ordinary
- CrossRefLink -> 3.8.3.3[2].[f]17.C

###### 3.8.1.1.a (Requirement Type)
The End Of Authority (EOA) is the location to which the train is authorised to move.
- WordTraceId: 72271
- atomic: true
- Legal Obligation: unknown
- implement: true
- ListNumberText: a)
- kind: ordinary

###### 3.8.1.1.b (Requirement Type)
The Target Speed at the EOA is the permitted speed at the EOA; when the target speed is not zero, the EOA is called the Limit of Authority (LOA). This target speed can be time limited.
- WordTraceId: 72356
- atomic: false
- Legal Obligation: unknown
- implement: true
- implementerEnhanced: The Target Speed at the EOA is the permitted speed at the EOA;
  when
  [CONDITION]
  the target speed is not zero, the EOA is called the Limit of Authority (LOA). This target speed can be
  time
  [TIME]
  limited.
- ListNumberText: b)
- kind: ordinary

###### 3.8.1.1.c (Requirement Type)
If no overlap exists, the Danger Point is a location beyond the EOA that can be reached by the front end of the train without a risk for a hazardous situation.
- WordTraceId: 72541
- atomic: true
- Legal Obligation: unknown
- implement: true
- implementerEnhanced: If
  [CONDITION]
  no overlap exists, the Danger Point is a location beyond the EOA that can be reached by the front end of the train without a risk for a hazardous situation.
- ListNumberText: c)
- kind: ordinary

###### 3.8.1.1.d (Requirement Type)
The end of an overlap (if used in the existing interlocking system) is a location beyond the Danger Point that can be reached by the front end of the train without a risk for a hazardous situation. This additional distance is only valid for a defined time.
- WordTraceId: 72702
- atomic: false
- Legal Obligation: unknown
- implement: true
- implementerEnhanced: The end of an overlap (
  if
  [CONDITION]
  used in the existing interlocking system) is a location beyond the Danger Point that can be reached by the front end of the train without a risk for a hazardous situation. This additional distance is only valid for a
  defined
  time
  [TIME]
  [WEAK]
  .
- ListNumberText: d)
- kind: ordinary

###### 3.8.1.1.e (Requirement Type)
A release speed is a speed limit under which the train is allowed to run in the vicinity of the EOA, when the target speed is zero. One release speed can be associated with the Danger Point, and another one with the overlap. Release speed can also be calculated on-board the train (see section 3.13.9.4).
- WordTraceId: 72959
- atomic: false
- Legal Obligation: unknown
- implement: true
- implementerEnhanced: A release speed is a speed limit under which the train is allowed to run in the vicinity of the EOA,
  when
  [CONDITION]
  the target speed is zero. One release speed can be associated with the Danger Point, and another one with the overlap. Release speed can also be calculated on-board the train (see section 3.13.9.4).
- ListNumberText: e)
- kind: ordinary
- CrossRefLink -> 3.13.9.4

###### 3.8.1.1.f (Requirement Type)
The MA can be split into several sections, The last one is called End Section.
- WordTraceId: 73293
- atomic: true
- Legal Obligation: unknown
- implement: true
- ListNumberText: f)
- kind: ordinary

###### 3.8.1.1.f.*[1] (Requirement Type)
A first time-out value can be attached to each section. This value will be used for the revocation of the associated route when the train has not entered into it yet. It is called the Section time-out.
- WordTraceId: 73372
- atomic: false
- Legal Obligation: unknown
- implement: true
- implementerEnhanced: A first time-out value can be attached to each section. This value will be used for the revocation of the associated route
  when
  [CONDITION]
  the train has not entered into it yet. It is called the Section time-out.
- ListNumberText: ·
- kind: ordinary

###### 3.8.1.1.f.*[2] (Requirement Type)
In addition, a second time-out value can be attached to the End Section of the MA. This second time-out will be used for the revocation of the last section when it is occupied by the train; it is called the End Section time-out.
- WordTraceId: 73575
- atomic: false
- Legal Obligation: unknown
- implement: true
- implementerEnhanced: In addition, a second time-out value can be attached to the End Section of the MA. This second time-out will be used for the revocation of the last section
  when
  [CONDITION]
  it is occupied by the train; it is called the End Section time-out.
- ListNumberText: ·
- kind: ordinary

##### 3.8.1.2 (Requirement Type)
The values of the time-outs possibly given in an MA shall take into account the time elapsed from the start of validity of information to the sending of the message.
- WordTraceId: 73804
- atomic: true
- Legal Obligation: mandatory
- implement: true
- implementerEnhanced: The values of the time-outs
  possibly
  [WEAK]
  given in an MA shall take into account the
  time
  [TIME]
  elapsed from the start of validity of information to the sending of the message.
- kind: ordinary

##### 3.8.1.3 (Requirement Type)
Note: A Danger Point can be (not exhaustive list):
- WordTraceId: 73970
- atomic: false
- Legal Obligation: not applicable
- implement: false
- implementerEnhanced: Note: A Danger Point can be (
  not exhaustive
  [WEAK]
  list):
- kind: Note

###### 3.8.1.3.*[1] (Requirement Type)
the entry point of an occupied block section (if the line is operated according to fixed block principles)
- WordTraceId: 74021
- atomic: true
- Legal Obligation: unknown
- implement: false
- implementerEnhanced: the entry point of an occupied block section (
  if
  [CONDITION]
  the line is operated according to fixed block principles)
- ListNumberText: ·
- kind: Note

###### 3.8.1.3.*[2] (Requirement Type)
the position of the safe rear end of a train (if the line is operated according to moving block principles)
- WordTraceId: 74128
- atomic: true
- Legal Obligation: unknown
- implement: false
- implementerEnhanced: the position of the safe rear end of a train (
  if
  [CONDITION]
  the line is operated according to moving block principles)
- ListNumberText: ·
- kind: Note

###### 3.8.1.3.*[3] (Requirement Type)
the fouling point of a switch, positioned for a route, conflicting with the current direction of movement of the train (both for fixed and moving block mode of operation)
- WordTraceId: 74236
- atomic: true
- Legal Obligation: unknown
- implement: false
- ListNumberText: ·
- kind: Note

##### 3.8.1.4 (Requirement Type)
Note: Traditionally the overlap is a piece of track (beyond the danger point), that is put at disposal of a train, to guarantee a non hazardous situation, also in case the driver should misjudge the stopping distance for the train. In ERTMS/ETCS the overlap can be used to improve the efficiency of the braking supervision.
- WordTraceId: 74407
- atomic: false
- Legal Obligation: not applicable
- implement: false
- implementerEnhanced: Note: Traditionally the overlap is a piece of track (beyond the danger point), that is put at disposal of a train, to guarantee a non hazardous situation, also
  in case
  [CONDITION]
  the
  driver
  [EXTERNAL]
  should misjudge the stopping distance for the train. In ERTMS/ETCS the overlap can be used to improve the efficiency of the braking supervision.
- kind: Note

##### 3.8.1.5 (Requirement Type)
Note: Time-out values can be given in the MA to cope with the following situations depending on the interlocking operations, i.e. the timers on-board will only reflect the situation trackside and when expired (on-board) the actions taken are restrictive:
- WordTraceId: 74731
- atomic: false
- Legal Obligation: not applicable
- implement: false
- implementerEnhanced: Note: Time-out values can be given in the MA to cope with the following situations depending on the interlocking operations, i.e. the timers on-board will only reflect the situation
  trackside
  [EXTERNAL]
  and
  when
  [CONDITION]
  expired (on-board) the actions taken are restrictive:
- kind: Note

###### 3.8.1.5.a (Requirement Type)
Section time-out or time-out for the speed at the EOA/LOA: When a signalman requests a route release of a part of a route not yet entered by the approaching train.
- WordTraceId: 74986
- atomic: true
- Legal Obligation: unknown
- implement: false
- implementerEnhanced: Section time-out or time-out for the speed at the EOA/LOA:
  When
  [CONDITION]
  a
  signalman
  [EXTERNAL]
  requests a route release of a part of a route
  not yet
  [TIME]
  entered by the approaching train.
- ListNumberText: a)
- kind: Note

###### 3.8.1.5.b (Requirement Type)
End Section time-out: When the train has entered the last part of a route, the automatic route release can be delayed to make sure that the train has come to a standstill before any switches inside the route can be moved.
- WordTraceId: 75150
- atomic: true
- Legal Obligation: unknown
- implement: false
- implementerEnhanced: End Section time-out:
  When
  [CONDITION]
  the train has entered the last part of a route, the automatic route release can be delayed to make sure that the train has come to a standstill before any switches inside the route can be moved.
- ListNumberText: b)
- kind: Note

###### 3.8.1.5.c (Requirement Type)
Time-out for an overlap: When the train has entered the last part of a route, the overlap associated with the route remains valid for a certain time to make sure that the train has successfully stopped before its end of authority. If the overlap is still unoccupied when the timer expires the interlocking revokes the overlap.
- WordTraceId: 75372
- atomic: false
- Legal Obligation: unknown
- implement: false
- implementerEnhanced: Time-out for an overlap:
  When
  [CONDITION]
  the train has entered the last part of a route, the overlap associated with the route remains valid for a certain
  time
  [TIME]
  to make sure that the train has successfully stopped before its end of authority.
  If
  [CONDITION]
  the overlap is still unoccupied
  when
  [CONDITION]
  the
  timer
  [TIME]
  expires the interlocking revokes the overlap.
- ListNumberText: c)
- kind: Note

##### 3.8.1.6 (Requirement Type)
Note:
If the trackside equipment does not have enough information to give the distance to End Of Authority (with target speed equal to zero) a target speed higher than zero can be given (speed at LOA, Limit Of Authority). It is the responsibility of the trackside to ensure that the safe distance beyond the EOA/LOA is long enough to brake the train from the target speed to a stand still without any hazardous situation. It is the responsibility of the on-board equipment to apply the brakes if no new information is received when the Limit of Authority is passed.
- WordTraceId: 75699
- atomic: false
- Legal Obligation: not applicable
- implement: false
- implementerEnhanced: Note:
  If
  [CONDITION]
  the
  trackside
  [EXTERNAL]
  equipment does not have enough information to give the distance to End Of Authority (with target speed equal to zero) a target speed higher than zero can be given (speed at LOA, Limit Of Authority). It is the responsibility of the
  trackside
  [EXTERNAL]
  to ensure that the safe distance beyond the EOA/LOA is long enough to brake the train from the target speed to a stand still without any hazardous situation. It is the responsibility of the
  on-board equipment
  [SELF]
  to apply the brakes
  if
  [CONDITION]
  no new information is received
  when
  [CONDITION]
  the Limit of Authority is passed.
- kind: Note

#### 3.8.2 (Requirement Type)
MA request to the RBC
- WordTraceId: 76266
- atomic: false
- Legal Obligation: not applicable
- implement: false
- implementerEnhanced: MA request to the
  RBC
  [EXTERNAL]
- kind: Heading

##### 3.8.2.1 (Requirement Type)
It shall be possible for the on-board equipment to request a new Movement Authority from the RBC.
- WordTraceId: 76288
- atomic: true
- Legal Obligation: mandatory
- implement: true
- implementerEnhanced: It shall be possible for the
  on-board equipment
  [SELF]
  to request a new Movement Authority from the
  RBC
  [EXTERNAL]
  .
- kind: ordinary

##### 3.8.2.2 (Requirement Type)
The parameters for requesting a new MA shall be given by the RBC.
- WordTraceId: 76387
- atomic: true
- Legal Obligation: mandatory
- implement: true
- implementerEnhanced: The parameters for requesting a new MA shall be given by the
  RBC
  [EXTERNAL]
  .
- kind: ordinary

##### 3.8.2.3 (Requirement Type)
In level 2/3, the following possibilities shall be available:
- WordTraceId: 76454
- atomic: true
- Legal Obligation: not applicable
- implement: false
- kind: Heading

###### 3.8.2.3.a (Requirement Type)
A defined time before the train reaches the pre-indication location (see section 3.13) for the EOA/LOA assuming it is running at the warning speed.
- WordTraceId: 76516
- atomic: true
- Legal Obligation: mandatory
- implement: true
- implementerEnhanced: A
  defined
  time
  [TIME]
  [WEAK]
  before the train reaches the pre-indication location (see section 3.13) for the EOA/LOA assuming it is running at the warning speed.
- ListNumberText: a)
- kind: ordinary
- CrossRefLink -> 3.13

###### 3.8.2.3.b (Requirement Type)
A defined time before the Section timer (not the End Section timer, not the Overlap timer) for any section of the MA expires, or before the LOA speed timer expires.
- WordTraceId: 76693
- atomic: true
- Legal Obligation: mandatory
- implement: true
- implementerEnhanced: A
  defined
  time
  [TIME]
  [WEAK]
  before the Section
  timer
  [TIME]
  (not the End Section
  timer
  [TIME]
  , not the Overlap
  timer
  [TIME]
  ) for any section of the MA expires, or before the LOA speed
  timer
  [TIME]
  expires.
- ListNumberText: b)
- kind: ordinary

###### 3.8.2.3.1 (Requirement Type)
Regards to the above possibilities, the MA request shall be triggered when the train front has passed the resulting location (regards a)/ time (regards b)
- WordTraceId: 76858
- atomic: true
- Legal Obligation: mandatory
- implement: true
- implementerEnhanced: Regards to the
  above
  [WEAK]
  possibilities, the MA request shall be triggered
  when
  [CONDITION]
  the train front has passed the resulting location (regards a)/
  time
  [TIME]
  (regards b)
- kind: ordinary

##### 3.8.2.4 (Requirement Type)
It shall be possible to define whether the MA request shall be repeated until a new MA is received or not and if so, the time between each repetition.
- WordTraceId: 77013
- atomic: false
- Legal Obligation: mandatory
- implement: true
- implementerEnhanced: It shall be possible to define
  whether
  [CONDITION]
  the MA request shall be
  repeated
  [LOOP]
  until
  [TIME]
  a new MA is received or not and
  if
  [CONDITION]
  so, the
  time
  [TIME]
  between each
  repetition
  [LOOP]
  .
- kind: ordinary

##### 3.8.2.5 (Requirement Type)
The given data shall be valid until new MA request parameters are given from the RBC.
- WordTraceId: 77164
- atomic: true
- Legal Obligation: mandatory
- implement: true
- implementerEnhanced: The given data shall be valid
  until
  [TIME]
  new MA request parameters are given from the
  RBC
  [EXTERNAL]
  .
- kind: ordinary

##### 3.8.2.6 (Requirement Type)
In case no MA request parameters are stored on-board and following an MA request no MA has been received, the request shall be repeated with a repetition cycle according to a fixed value (see appendix).
- WordTraceId: 77250
- atomic: true
- Legal Obligation: mandatory
- implement: true
- implementerEnhanced: In case
  [CONDITION]
  no MA request parameters are stored on-board and following an MA request no MA has been received, the request shall be
  repeated
  [LOOP]
  with a
  repetition
  [LOOP]
  cycle according to a fixed value (see appendix).
- kind: ordinary

##### 3.8.2.7 (Requirement Type)
In level 2/3: an MA request shall be sent to the RBC when the driver selects start.
- WordTraceId: 77453
- atomic: true
- Legal Obligation: mandatory
- implement: true
- implementerEnhanced: In level 2/3: an MA request shall be sent to the
  RBC
  [EXTERNAL]
  when
  [CONDITION]
  the
  driver
  [EXTERNAL]
  selects start.
- kind: ordinary

###### 3.8.2.7.1 (Requirement Type)
In level 0, 1, NTC: if a level 2/3 transition is announced and a communication session is already established, an MA request shall be sent to the RBC when the information "Track ahead free up to level 2/3 transition location" is received from balise group.
- WordTraceId: 77537
- atomic: true
- Legal Obligation: mandatory
- implement: true
- implementerEnhanced: In level 0, 1, NTC:
  if
  [CONDITION]
  a level 2/3 transition is announced and a communication session is already established, an MA request shall be sent to the
  RBC
  [EXTERNAL]
  when
  [CONDITION]
  the information "Track ahead free up to level 2/3 transition location" is received from
  balise group
  [EXTERNAL]
  .
- kind: ordinary

###### 3.8.2.7.2 (Requirement Type)
In level 0, 1, NTC: the ERTMS/ETCS on-board equipment shall also inform the RBC about the identity of the level 2/3 transition location balise group, as received through the information "Track ahead free up to level 2/3 transition location".
- WordTraceId: 77794
- atomic: true
- Legal Obligation: mandatory
- implement: true
- implementerEnhanced: In level 0, 1, NTC: the
  ERTMS/ETCS on-board equipment
  [SELF]
  shall also inform the
  RBC
  [EXTERNAL]
  about the identity of the level 2/3 transition location
  balise group
  [EXTERNAL]
  , as received through the information "
  Track ahead free up to level 2/3 transition location
  [LINKED_PHRASE]
  ".
- kind: ordinary
- KnownTermLink -> 3.8.2.7.1

###### 3.8.2.7.3 (Requirement Type)
In level 2/3: An MA request shall be sent to the RBC when any part of the track description is deleted according to A3.4, except for situations a, b, f, k.
- WordTraceId: 78036
- atomic: true
- Legal Obligation: mandatory
- implement: true
- implementerEnhanced: In level 2/3: An MA request shall be sent to the
  RBC
  [EXTERNAL]
  when
  [CONDITION]
  any part of the track description is deleted according to A3.4, except for situations a, b, f, k.
- kind: ordinary
- CrossRefLink -> A.3.4

##### 3.8.2.8 (Requirement Type)
Together with the MA request the on-board shall inform the RBC about the reason(s) why the MA request is sent:
- WordTraceId: 78192
- atomic: true
- Legal Obligation: mandatory
- implement: true
- implementerEnhanced: Together with the MA request the on-board shall inform the
  RBC
  [EXTERNAL]
  about the reason(s) why the MA request is sent:
- kind: ordinary

###### 3.8.2.8.a (Requirement Type)
Start selection by driver,
- WordTraceId: 78303
- atomic: true
- Legal Obligation: unknown
- implement: true
- implementerEnhanced: Start selection by
  driver
  [EXTERNAL]
  ,
- ListNumberText: a)
- kind: ordinary

###### 3.8.2.8.b (Requirement Type)
Time before reaching pre-indication location for the EOA/LOA reached,
- WordTraceId: 78330
- atomic: true
- Legal Obligation: unknown
- implement: true
- implementerEnhanced: Time
  [TIME]
  before reaching pre-indication location for the EOA/LOA reached,
- ListNumberText: b)
- kind: ordinary

###### 3.8.2.8.c (Requirement Type)
Time before a section timer or the LOA speed timer expires reached,
- WordTraceId: 78400
- atomic: true
- Legal Obligation: unknown
- implement: true
- implementerEnhanced: Time
  [TIME]
  before a section
  timer
  [TIME]
  or the LOA speed
  timer
  [TIME]
  expires reached,
- ListNumberText: c)
- kind: ordinary

###### 3.8.2.8.d (Requirement Type)
The track description has been deleted,
- WordTraceId: 78468
- atomic: true
- Legal Obligation: unknown
- implement: true
- ListNumberText: d)
- kind: ordinary

###### 3.8.2.8.e (Requirement Type)
Track ahead free up to level 2/3 transition location.
- WordTraceId: 78508
- atomic: true
- Legal Obligation: unknown
- implement: true
- implementerEnhanced: Track ahead free up to level 2/3 transition location
  [LINKED_PHRASE]
  .
- ListNumberText: e)
- kind: ordinary
- KnownTermLink -> 3.8.2.7.1

#### 3.8.3 (Requirement Type)
Structure of a Movement Authority (MA)
- WordTraceId: 78562
- atomic: false
- Legal Obligation: not applicable
- implement: false
- kind: Heading

##### 3.8.3.1 (Requirement Type)
The distance to End of Authority (EOA) can be composed of several sections.
- WordTraceId: 78601
- atomic: true
- Legal Obligation: unknown
- implement: true
- kind: ordinary

##### 3.8.3.2 (Requirement Type)
For each section composing the MA the following information shall be given;
- WordTraceId: 78677
- atomic: true
- Legal Obligation: not applicable
- implement: false
- implementerEnhanced: For each
  [LOOP]
  section composing the MA the following information shall be given;
- kind: Heading

###### 3.8.3.2.a (Requirement Type)
Length of the section
- WordTraceId: 78753
- atomic: true
- Legal Obligation: mandatory
- implement: true
- ListNumberText: a)
- kind: ordinary

###### 3.8.3.2.b (Requirement Type)
Optionally, Section time-out value and distance from beginning of section to Section timer stop location
- WordTraceId: 78775
- atomic: true
- Legal Obligation: mandatory
- implement: true
- implementerEnhanced: Optionally, Section time-out value and distance from beginning of section to Section
  timer
  [TIME]
  stop location
- ListNumberText: b)
- kind: ordinary

##### 3.8.3.3 (Requirement Type)
In addition, the End Section of the MA may include;
- WordTraceId: 78880
- atomic: true
- Legal Obligation: optional
- implement: true
- kind: ordinary

###### 3.8.3.3.a (Requirement Type)
End Section time-out value and distance from the End Section timer start location to the end of the last section
- WordTraceId: 78932
- atomic: true
- Legal Obligation: unknown
- implement: true
- implementerEnhanced: End Section time-out value and distance from the End Section
  timer
  [TIME]
  start location to the end of the last section
- ListNumberText: a)
- kind: ordinary

###### 3.8.3.3.b (Requirement Type)
Danger point information (distance from end of section to danger point, release speed related to danger point)
- WordTraceId: 79045
- atomic: true
- Legal Obligation: unknown
- implement: true
- ListNumberText: b)
- kind: ordinary

###### 3.8.3.3.c (Requirement Type)
Overlap information (distance from end of section to end of overlap, time-out, distance from Overlap timer start location to end of section, release speed related to overlap)
- WordTraceId: 79156
- atomic: true
- Legal Obligation: unknown
- implement: true
- implementerEnhanced: Overlap information (distance from end of section to end of overlap, time-out, distance from Overlap
  timer
  [TIME]
  start location to end of section, release speed related to overlap)
- ListNumberText: c)
- kind: ordinary

##### 3.8.3.3[2] (Requirement Type)
- WordTraceId: 79332
- atomic: false
- Legal Obligation: not applicable
- implement: false
- kind: Placeholder

###### 3.8.3.3[2].[f]17 (Requirement Type)
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- WordTraceId: 79357
- atomic: false
- Legal Obligation: not applicable
- implement: false
- kind: Figure

###### 3.8.3.3[2].[f]17.C (Requirement Type)
Figure {Figure 17}: Structure of an MA
- WordTraceId: 79357
- atomic: true
- Legal Obligation: unknown
- PlainText: Figure 17: Structure of an MA
- implement: false
- implementerEnhanced: Figure 17: Structure of an MA
- kind: Figure

###### 3.8.3.3[2].1 (Requirement Type)
Note: If only one section is given in the MA it is regarded as the End Section.
- WordTraceId: 79412
- atomic: false
- Legal Obligation: not applicable
- implement: false
- implementerEnhanced: Note:
  If
  [CONDITION]
  only one section is given in the MA it is regarded as the End Section.
- ListNumberText: 3.8.3.3.1
- kind: Note

##### 3.8.3.4 (Requirement Type)
The Section timer stop location shall be inside of the corresponding section.
- WordTraceId: 79492
- atomic: true
- Legal Obligation: mandatory
- implement: true
- implementerEnhanced: The Section
  timer
  [TIME]
  stop location shall be inside of the corresponding section.
- kind: ordinary

###### 3.8.3.4.1 (Requirement Type)
Note: the End Section and Overlap timer start locations may be outside their corresponding section. One example can be seen referring to figure 22c: An infill MA towards a signal at stop will replace the previous End Section by a new short End Section starting at the infill location reference and ending at the next main signal, however the End Section and Overlap timer start locations still have to be consistent with the Interlocking timer start locations. Another example is when a timer start location is in rear of the LRBG.
- WordTraceId: 79570
- atomic: false
- Legal Obligation: optional
- implement: false
- implementerEnhanced: Note: the End Section and Overlap
  timer
  [TIME]
  start locations may be outside their corresponding section. One example can be seen referring to figure 22c: An infill MA towards a signal at stop will replace the previous End Section by a new short End Section starting at the infill location reference and ending at the next main signal, however the End Section and Overlap
  timer
  [TIME]
  start locations still have to be consistent with the Interlocking
  timer
  [TIME]
  start locations. Another example is
  when
  [CONDITION]
  a
  timer
  [TIME]
  start location is in rear of the
  LRBG
  [EXTERNAL]
  .
- kind: Note
- CrossRefLink -> 3.8.5.3.3[4].[f]22c.C

##### 3.8.3.5 (Requirement Type)
In level 3, no time-outs shall be used.
- WordTraceId: 80102
- atomic: true
- Legal Obligation: mandatory
- implement: true
- kind: ordinary

###### 3.8.3.5.1 (Requirement Type)
Note: For level 3 functionality the split of responsibility between the RBC and the Interlocking has to be considered. Time-out of routes and related overlap can not be based on train position reports since the position report can be delayed compared to the real position of the train. The route release and revocation of routes can not be carried out by the interlocking until permitted by the RBC.
- WordTraceId: 80142
- atomic: false
- Legal Obligation: not applicable
- implement: false
- implementerEnhanced: Note: For level 3 functionality the split of responsibility between the
  RBC
  [EXTERNAL]
  and the Interlocking has to be considered. Time-out of routes and related overlap can not be based on train position reports since the position report can be delayed compared to the real position of the train. The route release and revocation of routes can not be carried out by the interlocking
  until
  [TIME]
  permitted by the
  RBC
  [EXTERNAL]
  .
- kind: Note

##### 3.8.3.6 (Requirement Type)
When an MA is transmitted by a balise group, the length of the first section shall refer to the balise co-ordinate system of that balise group.
- WordTraceId: 80542
- atomic: true
- Legal Obligation: mandatory
- implement: true
- implementerEnhanced: When
  [CONDITION]
  an MA is transmitted by a
  balise group
  [EXTERNAL]
  , the length of the first section shall refer to the
  balise
  [EXTERNAL]
  co-ordinate system of that
  balise group
  [EXTERNAL]
  .
- kind: ordinary

##### 3.8.3.7 (Requirement Type)
In case a main signal is at danger in level 1, the first section shall give the distance from the balise group at the main signal to the location of the main signal, i.e. the distance to EOA is given. Where available, information concerning danger point and overlap for this EOA may also be given.
- WordTraceId: 80686
- atomic: false
- Legal Obligation: mixed
- implement: true
- implementerEnhanced: In case
  [CONDITION]
  a main signal is at danger in level 1, the first section shall give the distance from the
  balise group
  [EXTERNAL]
  at the main signal to the location of the main signal, i.e. the distance to EOA is given.
  Where available
  [CONDITION]
  , information concerning danger point and overlap for this EOA may also be given.
- kind: ordinary

###### 3.8.3.7.1 (Requirement Type)
Justification: The balise group is not necessarily placed at the same location as the signal and thus an infill message (which includes the same information as the balise group at the main signal) could change the location of the EOA to a position closer to the train.
- WordTraceId: 80985
- atomic: false
- Legal Obligation: not applicable
- implement: false
- implementerEnhanced: Justification: The
  balise group
  [EXTERNAL]
  is not necessarily placed at the same location as the signal and thus an infill message (which includes the same information as the
  balise group
  [EXTERNAL]
  at the main signal) could change the location of the EOA to a position closer to the train.
- kind: Justification

##### 3.8.3.8 (Requirement Type)
In case the main signal is at danger in level 1, the on-board shall supervise the given distance (specified in section 3.8.3.7) as the distance to EOA.
- WordTraceId: 81255
- atomic: true
- Legal Obligation: mandatory
- implement: true
- implementerEnhanced: In case
  [CONDITION]
  the main signal is at danger in level 1, the on-board shall supervise the given distance (specified in section 3.8.3.7) as the distance to EOA.
- kind: ordinary
- CrossRefLink -> 3.8.3.7

##### 3.8.3.9 (Requirement Type)
When an MA is transmitted by radio from the RBC, the length of the first section shall refer to the balise co-ordinate system of the LRBG given in the same message.
- WordTraceId: 81436
- atomic: true
- Legal Obligation: mandatory
- implement: true
- implementerEnhanced: When
  [CONDITION]
  an MA is transmitted by radio from the
  RBC
  [EXTERNAL]
  , the length of the first section shall refer to the
  balise
  [EXTERNAL]
  co-ordinate system of the
  LRBG
  [EXTERNAL]
  given in the same message.
- kind: ordinary

##### 3.8.3.10 (Requirement Type)
It shall be possible to give the length of a section to any location in the track.
- WordTraceId: 81601
- atomic: true
- Legal Obligation: mandatory
- implement: true
- kind: ordinary

###### 3.8.3.10.1 (Requirement Type)
Note: A section can cover several blocks and is not restricted to block ends (see figures).
- WordTraceId: 81684
- atomic: false
- Legal Obligation: not applicable
- implement: false
- kind: Note

###### 3.8.3.10.1[2] (Requirement Type)
- WordTraceId: 81776
- atomic: false
- Legal Obligation: not applicable
- implement: false
- kind: Placeholder

###### 3.8.3.10.1[2].[f]18 (Requirement Type)
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- WordTraceId: 81800
- atomic: false
- Legal Obligation: not applicable
- implement: false
- kind: Figure

###### 3.8.3.10.1[2].[f]18.C (Requirement Type)
Figure {Figure 18}: Distance to End Of Authority when no time-outs are needed
- WordTraceId: 81800
- atomic: true
- Legal Obligation: unknown
- PlainText: Figure 18: Distance to End Of Authority when no time-outs are needed
- implement: false
- implementerEnhanced: Figure 18: Distance to End Of Authority
  when
  [CONDITION]
  no time-outs are needed
- kind: Figure

###### 3.8.3.10.1[3] (Requirement Type)
- WordTraceId: 81896
- atomic: false
- Legal Obligation: not applicable
- implement: false
- kind: Placeholder

###### 3.8.3.10.1[3].[f]19 (Requirement Type)
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- WordTraceId: 81921
- atomic: false
- Legal Obligation: not applicable
- implement: false
- kind: Figure

###### 3.8.3.10.1[3].[f]19.C (Requirement Type)
Figure {Figure 19} : Distance to End Of Authority when time-outs might be needed
- WordTraceId: 81921
- atomic: true
- Legal Obligation: unknown
- PlainText: Figure 19 : Distance to End Of Authority when time-outs might be needed
- implement: false
- implementerEnhanced: Figure 19 : Distance to End Of Authority
  when
  [CONDITION]
  time-outs might be needed
- kind: Figure

##### 3.8.3.11 (Requirement Type)
In moving block operation the MA shall never exceed the min safe rear end of the preceding train.
- WordTraceId: 82018
- atomic: true
- Legal Obligation: mandatory
- implement: true
- kind: ordinary

##### 3.8.3.11[2] (Requirement Type)
- WordTraceId: 82117
- atomic: false
- Legal Obligation: not applicable
- implement: false
- kind: Placeholder

###### 3.8.3.11[2].[f]20 (Requirement Type)
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- WordTraceId: 82144
- atomic: false
- Legal Obligation: not applicable
- implement: false
- kind: Figure

###### 3.8.3.11[2].[f]20.C (Requirement Type)
Figure {Figure 20}: MA in moving block operation.
- WordTraceId: 82144
- atomic: true
- Legal Obligation: unknown
- PlainText: Figure 20: MA in moving block operation.
- implement: false
- implementerEnhanced: Figure 20: MA in moving block operation.
- kind: Figure

#### 3.8.4 (Requirement Type)
Use of the MA on board the train
- WordTraceId: 82211
- atomic: false
- Legal Obligation: not applicable
- implement: false
- kind: Heading

##### 3.8.4.1 (Requirement Type)
End Section Time-Out
- WordTraceId: 82244
- atomic: false
- Legal Obligation: not applicable
- implement: false
- kind: Heading

###### 3.8.4.1.1 (Requirement Type)
The End Section timer shall be started on-board when the train passes the End Section timer start location given by trackside with its max safe front end.
- WordTraceId: 82265
- atomic: true
- Legal Obligation: mandatory
- implement: true
- implementerEnhanced: The End Section
  timer
  [TIME]
  shall be started on-board
  when
  [CONDITION]
  the train passes the End Section
  timer
  [TIME]
  start location given by
  trackside
  [EXTERNAL]
  with its max safe front end.
- kind: ordinary

###### 3.8.4.1.2 (Requirement Type)
When the End Section timer value becomes greater than the time-out value given by trackside, the following shall apply:
- WordTraceId: 82420
- atomic: true
- Legal Obligation: not applicable
- implement: false
- implementerEnhanced: When
  [CONDITION]
  the End Section
  timer
  [TIME]
  value becomes greater than the time-out value given by
  trackside
  [EXTERNAL]
  , the following shall apply:
- kind: Heading

###### 3.8.4.1.2.a (Requirement Type)
The EOA/LOA shall be withdrawn to the current position of the train. Refer to appendix A.3.4 for the exhaustive list of location based information stored on-board, which shall be deleted accordingly;
- WordTraceId: 82540
- atomic: false
- Legal Obligation: mandatory
- implement: true
- ListNumberText: a)
- kind: ordinary
- CrossRefLink -> A.3.4

###### 3.8.4.1.2.b (Requirement Type)
if any, a non zero target speed value at the EOA/LOA shall be set to zero.
- WordTraceId: 82740
- atomic: true
- Legal Obligation: mandatory
- implement: true
- implementerEnhanced: if
  [CONDITION]
  any, a non zero target speed value at the EOA/LOA shall be set to zero.
- ListNumberText: b)
- kind: ordinary

###### 3.8.4.1.3 (Requirement Type)
In case no End Section timer is running when the on-board receives a new MA with an End Section timer start location in rear of the max safe front end of the train, the on-board shall consider that the End Section timer value became greater than its time-out value and apply 3.8.4.1.2.
- WordTraceId: 82815
- atomic: true
- Legal Obligation: mandatory
- implement: true
- implementerEnhanced: In case
  [CONDITION]
  no End Section
  timer
  [TIME]
  is running
  when
  [CONDITION]
  the on-board receives a new MA with an End Section
  timer
  [TIME]
  start location in rear of the max safe front end of the train, the on-board shall consider that the End Section
  timer
  [TIME]
  value became greater than its time-out value and apply 3.8.4.1.2.
- kind: ordinary
- CrossRefLink -> 3.8.4.1.2

###### 3.8.4.1.3.1 (Requirement Type)
Justification: in this case the train is already beyond the timer start location, therefore it is impossible to determine when that location was crossed and so what share of the time-out value has elapsed since the crossing event. The safe assumption is to consider that the time-out value has been exceeded and therefore that the End Section will soon be released by the Interlocking.
- WordTraceId: 83101
- atomic: false
- Legal Obligation: not applicable
- implement: false
- implementerEnhanced: Justification: in this case the train is already beyond the
  timer
  [TIME]
  start location, therefore it is impossible to determine
  when
  [CONDITION]
  that location was crossed and so what share of the time-out value has elapsed since the crossing event. The safe assumption is to consider that the time-out value has been exceeded and therefore that the End Section will soon be released by the Interlocking.
- kind: Justification

###### 3.8.4.1.4 (Requirement Type)
In case an End Section timer is already running when the on-board receives a new MA with an End Section timer start location in rear of the max safe front end of the train, the on-board shall keep the End Section timer running but replace the time-out value with the value received with the new MA.
- WordTraceId: 83487
- atomic: true
- Legal Obligation: mandatory
- implement: true
- implementerEnhanced: In case
  [CONDITION]
  an End Section
  timer
  [TIME]
  is already running
  when
  [CONDITION]
  the on-board receives a new MA with an End Section
  timer
  [TIME]
  start location in rear of the max safe front end of the train, the on-board shall keep the End Section
  timer
  [TIME]
  running but replace the time-out value with the value received with the new MA.
- kind: ordinary

###### 3.8.4.1.4.1 (Requirement Type)
Justification: this allows repetition of the MA via RBC (e.g. acknowledgment of current MA was lost) without unintentionally affecting the End Section timer.
- WordTraceId: 83786
- atomic: false
- Legal Obligation: not applicable
- implement: false
- implementerEnhanced: Justification: this allows
  repetition
  [LOOP]
  of the MA via
  RBC
  [EXTERNAL]
  (
  e.g.
  [WEAK]
  acknowledgment of current MA was lost) without unintentionally affecting the End Section
  timer
  [TIME]
  .
- kind: Justification

##### 3.8.4.2 (Requirement Type)
Section Time-Outs
- WordTraceId: 83944
- atomic: false
- Legal Obligation: not applicable
- implement: false
- kind: Heading

###### 3.8.4.2.1 (Requirement Type)
The on-board shall start a Section timer for each section:
- WordTraceId: 83962
- atomic: true
- Legal Obligation: mandatory
- implement: true
- implementerEnhanced: The on-board shall start a Section
  timer
  [TIME]
  for each
  [LOOP]
  section:
- kind: ordinary

###### 3.8.4.2.1.a (Requirement Type)
For Level 2: at the value of the time stamp of the message including the MA.
- WordTraceId: 84021
- atomic: true
- Legal Obligation: unknown
- implement: true
- implementerEnhanced: For Level 2: at the value of the
  time
  [TIME]
  stamp of the message including the MA.
- ListNumberText: a)
- kind: ordinary

###### 3.8.4.2.1.b (Requirement Type)
For Level 1: at the time of passage over the first encountered balise of the balise group giving the MA.
- WordTraceId: 84098
- atomic: true
- Legal Obligation: unknown
- implement: true
- implementerEnhanced: For Level 1: at the
  time
  [TIME]
  of passage over the first encountered
  balise
  [EXTERNAL]
  of the
  balise group
  [EXTERNAL]
  giving the MA.
- ListNumberText: b)
- kind: ordinary

###### 3.8.4.2.1.1 (Requirement Type)
Justification for b): This is to ensure that the timer is always started before or at the same time as the related variable information is received. Thus the timer start is independent of in which balise the variable information is given.
- WordTraceId: 84203
- atomic: false
- Legal Obligation: not applicable
- implement: false
- implementerEnhanced: Justification for b): This is to ensure that the
  timer
  [TIME]
  is always started before or at the same
  time
  [TIME]
  as the related variable information is received. Thus the
  timer
  [TIME]
  start is independent of in which
  balise
  [EXTERNAL]
  the variable information is given.
- kind: Justification

###### 3.8.4.2.2 (Requirement Type)
When a Section timer value becomes greater than the time-out value given by trackside, the following shall apply:
- WordTraceId: 84443
- atomic: true
- Legal Obligation: not applicable
- implement: false
- implementerEnhanced: When
  [CONDITION]
  a Section
  timer
  [TIME]
  value becomes greater than the time-out value given by
  trackside
  [EXTERNAL]
  , the following shall apply:
- kind: Heading

###### 3.8.4.2.2.a (Requirement Type)
the EOA/LOA and the SvL shall be withdrawn to the entry point of the revoked section. Refer to appendix A.3.4 for the exhaustive list of location based information stored on-board, which shall be deleted accordingly;
- WordTraceId: 84557
- atomic: false
- Legal Obligation: mandatory
- implement: true
- ListNumberText: a)
- kind: ordinary
- CrossRefLink -> A.3.4

###### 3.8.4.2.2.b (Requirement Type)
the National/ Default Value of the Release Speed shall apply ;
- WordTraceId: 84774
- atomic: true
- Legal Obligation: mandatory
- implement: true
- ListNumberText: b)
- kind: ordinary

###### 3.8.4.2.2.c (Requirement Type)
if any, a non zero target speed value at the EOA/LOA shall be set to zero.
- WordTraceId: 84837
- atomic: true
- Legal Obligation: mandatory
- implement: true
- implementerEnhanced: if
  [CONDITION]
  any, a non zero target speed value at the EOA/LOA shall be set to zero.
- ListNumberText: c)
- kind: ordinary

###### 3.8.4.2.2.1 (Requirement Type)
Intentionally deleted.
- WordTraceId: 84912
- atomic: false
- Legal Obligation: not applicable
- implement: false
- kind: Placeholder

###### 3.8.4.2.3 (Requirement Type)
The Section timer shall be stopped when the min safe front end of the train has passed the associated Section timer stop location.
- WordTraceId: 84935
- atomic: true
- Legal Obligation: mandatory
- implement: true
- implementerEnhanced: The Section
  timer
  [TIME]
  shall be stopped
  when
  [CONDITION]
  the min safe front end of the train has passed the associated Section
  timer
  [TIME]
  stop location.
- kind: ordinary

##### 3.8.4.3 (Requirement Type)
Time-out of the speed associated with the EOA/LOA
- WordTraceId: 85066
- atomic: false
- Legal Obligation: not applicable
- implement: false
- kind: Heading

###### 3.8.4.3.1 (Requirement Type)
The on-board shall start a timer for the speed at the EOA/LOA:
- WordTraceId: 85116
- atomic: true
- Legal Obligation: mandatory
- implement: true
- implementerEnhanced: The on-board shall start a
  timer
  [TIME]
  for the speed at the EOA/LOA:
- kind: ordinary

###### 3.8.4.3.1.a (Requirement Type)
For Level 2: at the value of the time stamp of the message including the MA.
- WordTraceId: 85179
- atomic: true
- Legal Obligation: unknown
- implement: true
- implementerEnhanced: For Level 2: at the value of the
  time
  [TIME]
  stamp of the message including the MA.
- ListNumberText: a)
- kind: ordinary

###### 3.8.4.3.1.b (Requirement Type)
For Level 1: at the time of passage over the first encountered balise of the balise group giving the MA.
- WordTraceId: 85256
- atomic: true
- Legal Obligation: unknown
- implement: true
- implementerEnhanced: For Level 1: at the
  time
  [TIME]
  of passage over the first encountered
  balise
  [EXTERNAL]
  of the
  balise group
  [EXTERNAL]
  giving the MA.
- ListNumberText: b)
- kind: ordinary

###### 3.8.4.3.1.1 (Requirement Type)
Justification for b): This is to ensure that the timer is always started before or at the same time as the related variable information is received. Thus the timer start is independent of in which balise the variable information is given.
- WordTraceId: 85361
- atomic: false
- Legal Obligation: not applicable
- implement: false
- implementerEnhanced: Justification for b): This is to ensure that the
  timer
  [TIME]
  is always started before or at the same
  time
  [TIME]
  as the related variable information is received. Thus the
  timer
  [TIME]
  start is independent of in which
  balise
  [EXTERNAL]
  the variable information is given.
- kind: Justification

###### 3.8.4.3.2 (Requirement Type)
When the LOA speed timer value becomes greater than the time-out value given by trackside, the speed associated with the EOA/LOA shall be set to zero (i.e. the Limit of Authority becomes an End of Authority and the SvL is defined on-board according to 3.8.4.5). Refer to appendix A.3.4 for the exhaustive list of location based information stored on-board, which shall be deleted accordingly.
- WordTraceId: 85600
- atomic: false
- Legal Obligation: mandatory
- implement: true
- implementerEnhanced: When
  [CONDITION]
  the LOA speed
  timer
  [TIME]
  value becomes greater than the time-out value given by
  trackside
  [EXTERNAL]
  , the speed associated with the EOA/LOA shall be set to zero (i.e. the Limit of Authority becomes an End of Authority and the SvL is defined on-board according to 3.8.4.5). Refer to appendix A.3.4 for the exhaustive list of location based information stored on-board, which shall be deleted accordingly.
- kind: ordinary
- CrossRefLink -> 3.8.4.5
- CrossRefLink -> A.3.4

##### 3.8.4.4 (Requirement Type)
Time-out of Overlap
- WordTraceId: 85994
- atomic: false
- Legal Obligation: not applicable
- implement: false
- kind: Heading

###### 3.8.4.4.1 (Requirement Type)
The Overlap timer shall be started on-board when the train passes the Overlap timer start location given by trackside with its max safe front end. The timer shall be considered as started even if a time-out value “infinite” is given.
- WordTraceId: 86014
- atomic: false
- Legal Obligation: mandatory
- implement: true
- implementerEnhanced: The Overlap
  timer
  [TIME]
  shall be started on-board
  when
  [CONDITION]
  the train passes the Overlap
  timer
  [TIME]
  start location given by
  trackside
  [EXTERNAL]
  with its max safe front end. The
  timer
  [TIME]
  shall be considered as started
  even
  if
  [CONDITION]
  [WEAK]
  a time-out value “infinite” is given.
- kind: ordinary

###### 3.8.4.4.2 (Requirement Type)
When the Overlap timer value becomes greater than the time-out value given by trackside, the following shall apply:
- WordTraceId: 86248
- atomic: true
- Legal Obligation: not applicable
- implement: false
- implementerEnhanced: When
  [CONDITION]
  the Overlap
  timer
  [TIME]
  value becomes greater than the time-out value given by
  trackside
  [EXTERNAL]
  , the following shall apply:
- kind: Heading

###### 3.8.4.4.2.a (Requirement Type)
the overlap information shall be deleted, i.e. the Supervised Location shall be withdrawn to the Danger Point if there is any or else to the EOA. Refer to appendix A.3.4 for the exhaustive list of location based information stored on-board, which shall be deleted accordingly.
- WordTraceId: 86364
- atomic: false
- Legal Obligation: mandatory
- implement: true
- implementerEnhanced: the overlap information shall be deleted, i.e. the Supervised Location shall be withdrawn to the Danger Point
  if
  [CONDITION]
  there is any or else to the EOA. Refer to appendix A.3.4 for the exhaustive list of location based information stored on-board, which shall be deleted accordingly.
- ListNumberText: a)
- kind: ordinary
- CrossRefLink -> A.3.4

###### 3.8.4.4.2.b (Requirement Type)
the release speed associated with the Overlap shall be deleted
- WordTraceId: 86641
- atomic: true
- Legal Obligation: mandatory
- implement: true
- ListNumberText: b)
- kind: ordinary

###### 3.8.4.4.2.c (Requirement Type)
if any, a non zero target speed value at the EOA/LOA shall be set to zero.
- WordTraceId: 86704
- atomic: true
- Legal Obligation: mandatory
- implement: true
- implementerEnhanced: if
  [CONDITION]
  any, a non zero target speed value at the EOA/LOA shall be set to zero.
- ListNumberText: c)
- kind: ordinary

###### 3.8.4.4.3 (Requirement Type)
If the train comes to a standstill after the Overlap timer has been started, the on-board shall consider that the Overlap timer value became greater than its time-out value and shall apply 3.8.4.4.2.
- WordTraceId: 86779
- atomic: false
- Legal Obligation: mandatory
- implement: true
- implementerEnhanced: If
  [CONDITION]
  the train comes to a standstill
  after
  [TIME]
  the Overlap
  timer
  [TIME]
  has been started, the on-board shall consider that the Overlap
  timer
  [TIME]
  value became greater than its time-out value and shall apply 3.8.4.4.2.
- kind: ordinary
- CrossRefLink -> 3.8.4.4.2

###### 3.8.4.4.4 (Requirement Type)
In case no Overlap timer is running when the on-board receives a new MA with an Overlap timer start location in rear of the max safe front end of the train, the on-board shall consider that the Overlap timer value became greater than its time-out value and shall apply 3.8.4.4.2.
- WordTraceId: 86979
- atomic: false
- Legal Obligation: mandatory
- implement: true
- implementerEnhanced: In case
  [CONDITION]
  no Overlap
  timer
  [TIME]
  is running
  when
  [CONDITION]
  the on-board receives a new MA with an Overlap
  timer
  [TIME]
  start location in rear of the max safe front end of the train, the on-board shall consider that the Overlap
  timer
  [TIME]
  value became greater than its time-out value and shall apply 3.8.4.4.2.
- kind: ordinary
- CrossRefLink -> 3.8.4.4.2

###### 3.8.4.4.4.1 (Requirement Type)
Justification: in this case the train is already beyond the timer start location, therefore it is impossible to determine when that location was crossed and so what share of the time-out value has elapsed since the crossing event. The safe assumption is to consider that the time-out value has been exceeded and therefore that the Overlap will soon be released by the Interlocking.
- WordTraceId: 87259
- atomic: false
- Legal Obligation: not applicable
- implement: false
- implementerEnhanced: Justification: in this case the train is already beyond the
  timer
  [TIME]
  start location, therefore it is impossible to determine
  when
  [CONDITION]
  that location was crossed and so what share of the time-out value has elapsed since the crossing event. The safe assumption is to consider that the time-out value has been exceeded and therefore that the Overlap will soon be released by the Interlocking.
- kind: Justification

###### 3.8.4.4.5 (Requirement Type)
In case an Overlap timer is already running when the on-board receives a new MA with an Overlap timer start location in rear of the max safe front end of the train, the on-board shall keep the Overlap timer running but replace the Overlap time-out value with the value received with the new MA.
- WordTraceId: 87641
- atomic: true
- Legal Obligation: mandatory
- implement: true
- implementerEnhanced: In case
  [CONDITION]
  an Overlap
  timer
  [TIME]
  is already running
  when
  [CONDITION]
  the on-board receives a new MA with an Overlap
  timer
  [TIME]
  start location in rear of the max safe front end of the train, the on-board shall keep the Overlap
  timer
  [TIME]
  running but replace the Overlap time-out value with the value received with the new MA.
- kind: ordinary

###### 3.8.4.4.5.1 (Requirement Type)
Justification: this allows repetition of the MA via RBC (e.g. acknowledgment of current MA was lost) without unintentionally affecting the Overlap timer.
- WordTraceId: 87936
- atomic: false
- Legal Obligation: not applicable
- implement: false
- implementerEnhanced: Justification: this allows
  repetition
  [LOOP]
  of the MA via
  RBC
  [EXTERNAL]
  (
  e.g.
  [WEAK]
  acknowledgment of current MA was lost) without unintentionally affecting the Overlap
  timer
  [TIME]
  .
- kind: Justification

##### 3.8.4.5 (Requirement Type)
Supervised Location
- WordTraceId: 88090
- atomic: false
- Legal Obligation: not applicable
- implement: false
- kind: Heading

###### 3.8.4.5.1 (Requirement Type)
The Supervised Location (SvL) shall be defined on board as;
- WordTraceId: 88110
- atomic: true
- Legal Obligation: mandatory
- implement: true
- kind: ordinary

###### 3.8.4.5.1.a (Requirement Type)
the end of overlap (if any and before time-out).
- WordTraceId: 88170
- atomic: true
- Legal Obligation: unknown
- implement: true
- implementerEnhanced: the end of overlap (
  if
  [CONDITION]
  any and before time-out).
- ListNumberText: a)
- kind: ordinary

###### 3.8.4.5.1.b (Requirement Type)
if not, the Danger Point (if any).
- WordTraceId: 88219
- atomic: true
- Legal Obligation: unknown
- implement: true
- implementerEnhanced: if
  [CONDITION]
  not, the Danger Point (
  if
  [CONDITION]
  any).
- ListNumberText: b)
- kind: ordinary

###### 3.8.4.5.1.c (Requirement Type)
if not, the End Of Authority.
- WordTraceId: 88254
- atomic: true
- Legal Obligation: unknown
- implement: true
- implementerEnhanced: if
  [CONDITION]
  not, the End Of Authority.
- ListNumberText: c)
- kind: ordinary

###### 3.8.4.5.2 (Requirement Type)
As long as a Limit of Authority is supervised, no SvL shall be defined on-board.
- WordTraceId: 88284
- atomic: true
- Legal Obligation: mandatory
- implement: true
- implementerEnhanced: As long as
  [TIME]
  a Limit of Authority is supervised, no SvL shall be defined on-board.
- kind: ordinary

##### 3.8.4.6 (Requirement Type)
Infill MA (level 1 only)
- WordTraceId: 88365
- atomic: false
- Legal Obligation: not applicable
- implement: false
- kind: Heading

###### 3.8.4.6.1 (Requirement Type)
An MA given by an infill device is called an infill MA.
- WordTraceId: 88390
- atomic: true
- Legal Obligation: unknown
- implement: false
- kind: Definition

###### 3.8.4.6.2 (Requirement Type)
An infill MA shall be evaluated on-board only if the on-board equipment is in FS or LS mode.
- WordTraceId: 88446
- atomic: true
- Legal Obligation: mandatory
- implement: true
- implementerEnhanced: An infill MA shall be evaluated on-board only
  if
  [CONDITION]
  the
  on-board equipment
  [SELF]
  is in FS or LS mode.
- kind: ordinary

###### 3.8.4.6.3 (Requirement Type)
The infill information shall include the identity of the balise group at the next main signal i.e. the identity of the balise group giving the information that is transmitted in advance by the infill device.
- WordTraceId: 88539
- atomic: true
- Legal Obligation: mandatory
- implement: true
- implementerEnhanced: The infill information shall include the identity of the
  balise group
  [EXTERNAL]
  at the next main signal i.e. the identity of the
  balise group
  [EXTERNAL]
  giving the information that is transmitted in advance by the infill device.
- kind: ordinary

###### 3.8.4.6.4 (Requirement Type)
An infill MA shall be evaluated on-board only if the linking information, regarding the main signal balise group to which it refers, is available.
- WordTraceId: 88747
- atomic: true
- Legal Obligation: mandatory
- implement: true
- implementerEnhanced: An infill MA shall be evaluated on-board only
  if
  [CONDITION]
  the linking information, regarding the main signal
  balise group
  [EXTERNAL]
  to which it refers, is available.
- kind: ordinary

###### 3.8.4.6.5 (Requirement Type)
The on-board shall start a Section timer for each section beyond the next main signal:
- WordTraceId: 88894
- atomic: true
- Legal Obligation: mandatory
- implement: true
- implementerEnhanced: The on-board shall start a Section
  timer
  [TIME]
  for each
  [LOOP]
  section beyond the next main signal:
- kind: ordinary

###### 3.8.4.6.5.a (Requirement Type)
When the infill information is received from a balise group at the time of passing the first encountered balise of the infill balise group.
- WordTraceId: 88981
- atomic: true
- Legal Obligation: unknown
- implement: true
- implementerEnhanced: When
  [CONDITION]
  the infill information is received from a
  balise group
  [EXTERNAL]
  at the
  time
  [TIME]
  of passing the first encountered
  balise
  [EXTERNAL]
  of the infill
  balise group
  [EXTERNAL]
  .
- ListNumberText: a)
- kind: ordinary

###### 3.8.4.6.5.b (Requirement Type)
When the infill information is received from a loop at the time of receiving the loop message.
- WordTraceId: 89121
- atomic: true
- Legal Obligation: unknown
- implement: true
- implementerEnhanced: When
  [CONDITION]
  the infill information is received from a
  loop
  [EXTERNAL]
  at the
  time
  [TIME]
  of receiving the
  loop
  [EXTERNAL]
  message.
- ListNumberText: b)
- kind: ordinary

###### 3.8.4.6.5.c (Requirement Type)
When the infill information is received from a radio infill unit at the value of the time stamp of the radio infill message including the MA.
- WordTraceId: 89216
- atomic: true
- Legal Obligation: unknown
- implement: true
- implementerEnhanced: When
  [CONDITION]
  the infill information is received from a
  radio infill unit
  [EXTERNAL]
  at the value of the
  time
  [TIME]
  stamp of the radio infill message including the MA.
- ListNumberText: c)
- kind: ordinary

#### 3.8.5 (Requirement Type)
MA Update
- WordTraceId: 89358
- atomic: false
- Legal Obligation: not applicable
- implement: false
- kind: Heading

##### 3.8.5.1 (Requirement Type)
A new MA shall replace a previously received MA in the following ways:
- WordTraceId: 89368
- atomic: true
- Legal Obligation: not applicable
- implement: false
- kind: Heading

###### 3.8.5.1.a (Requirement Type)
When the new MA is given from a balise group at a main signal (i.e. not infill information) or from the RBC all data included in the previous MA shall be replaced by the new data.
- WordTraceId: 89439
- atomic: true
- Legal Obligation: mandatory
- implement: true
- implementerEnhanced: When
  [CONDITION]
  the new MA is given from a
  balise group
  [EXTERNAL]
  at a main signal (i.e. not infill information) or from the
  RBC
  [EXTERNAL]
  all data included in the previous MA shall be replaced by the new data.
- ListNumberText: a)
- kind: ordinary

###### 3.8.5.1.b (Requirement Type)
When the new MA is given as infill information all data beyond the announced balise group at the next main signal shall be replaced.
- WordTraceId: 89620
- atomic: true
- Legal Obligation: mandatory
- implement: true
- implementerEnhanced: When
  [CONDITION]
  the new MA is given as infill information all data beyond the announced
  balise group
  [EXTERNAL]
  at the next main signal shall be replaced.
- ListNumberText: b)
- kind: ordinary

###### 3.8.5.1.1 (Requirement Type)
Note: This refers to all information included in the MA as listed in section 3.8.1.1 and the Signalling related speed restriction (see section 3.11.6).
- WordTraceId: 89753
- atomic: false
- Legal Obligation: mandatory
- implement: false
- kind: Note
- CrossRefLink -> 3.8.1.1
- CrossRefLink -> 3.11.6

###### 3.8.5.1.2 (Requirement Type)
When an infill MA is received, the on-board shall start a new MA section at the infill location reference, i.e. the balise group at the next main signal (see 3.6.2.3.1).
- WordTraceId: 89963
- atomic: true
- Legal Obligation: mandatory
- implement: true
- implementerEnhanced: When
  [CONDITION]
  an infill MA is received, the on-board shall start a new MA section at the infill location reference, i.e. the
  balise group
  [EXTERNAL]
  at the next main signal (see 3.6.2.3.1).
- kind: ordinary
- CrossRefLink -> 3.6.2.3.1

###### 3.8.5.1.3 (Requirement Type)
If the SvL defined from the new MA is closer than the one supervised with the former MA, this shall be considered by the on-board equipment as an MA shortening. Refer to appendix A.3.4 for the exhaustive list of location based information stored on-board, which shall be deleted accordingly.
- WordTraceId: 90133
- atomic: false
- Legal Obligation: mandatory
- implement: true
- implementerEnhanced: If
  [CONDITION]
  the SvL defined from the new MA is closer than the one supervised with the former MA, this shall be considered by the
  on-board equipment
  [SELF]
  as an MA shortening. Refer to appendix A.3.4 for the exhaustive list of location based information stored on-board, which shall be deleted accordingly.
- kind: ordinary
- CrossRefLink -> A.3.4

###### 3.8.5.1.4 (Requirement Type)
If a new MA defines an SvL while the on-board was supervising an LOA, this shall always be considered by the on-board equipment as an MA shortening regardless of the SvL location. Refer to appendix A.3.4 for the exhaustive list of location based information stored on-board, which shall be deleted accordingly.
- WordTraceId: 90425
- atomic: false
- Legal Obligation: mandatory
- implement: false
- implementerEnhanced: If
  [CONDITION]
  a new MA defines an SvL
  while
  [TIME]
  the on-board was supervising an LOA, this shall always be considered by the
  on-board equipment
  [SELF]
  as an MA shortening regardless of the SvL location. Refer to appendix A.3.4 for the exhaustive list of location based information stored on-board, which shall be deleted accordingly.
- kind: Definition
- CrossRefLink -> A.3.4

##### 3.8.5.2 (Requirement Type)
It shall be possible to update the length of the current section by means of repositioning information (see section 3.8.5.3).
- WordTraceId: 90736
- atomic: true
- Legal Obligation: mandatory
- implement: true
- kind: ordinary
- CrossRefLink -> 3.8.5.3

###### 3.8.5.2.1 (Requirement Type)
Note: The current section need not be the end section.
- WordTraceId: 90891
- atomic: false
- Legal Obligation: not applicable
- implement: false
- kind: Note

###### 3.8.5.2.2 (Requirement Type)
Repositioning information contained in a balise group message shall only be evaluated if linking information has announced a following balise group as unknown but containing repositioning information.
- WordTraceId: 90946
- atomic: true
- Legal Obligation: mandatory
- implement: true
- implementerEnhanced: Repositioning information contained in a
  balise group
  [EXTERNAL]
  message shall only be evaluated
  if
  [CONDITION]
  linking information has announced a following
  balise group
  [EXTERNAL]
  as unknown but containing repositioning information.
- kind: ordinary

###### 3.8.5.2.3 (Requirement Type)
A balise group message containing a movement authority shall not contain repositioning information for the same direction.
- WordTraceId: 91147
- atomic: true
- Legal Obligation: mandatory
- implement: true
- implementerEnhanced: A
  balise group
  [EXTERNAL]
  message containing a movement authority shall not contain repositioning information for the same direction.
- kind: ordinary

###### 3.8.5.2.3.1 (Requirement Type)
Note: It is possible to combine repositioning with an infill MA.
- WordTraceId: 91270
- atomic: false
- Legal Obligation: not applicable
- implement: false
- kind: Note

###### 3.8.5.2.4 (Requirement Type)
The reception of repositioning information or of a new MA with an LOA shall not be considered as an MA shortening by the on-board equipment.
- WordTraceId: 91335
- atomic: true
- Legal Obligation: mandatory
- implement: true
- implementerEnhanced: The reception of repositioning information or of a new MA with an LOA shall not be considered as an MA shortening by the
  on-board equipment
  [SELF]
  .
- kind: ordinary

##### 3.8.5.3 (Requirement Type)
Examples of MA update
- WordTraceId: 91476
- atomic: false
- Legal Obligation: not applicable
- implement: false
- kind: Heading

###### 3.8.5.3.1 (Requirement Type)
Note: In the following examples on how to update an MA are given. The examples are not exhaustive.
- WordTraceId: 91498
- atomic: false
- Legal Obligation: not applicable
- implement: false
- implementerEnhanced: Note: In the following examples on how to update an MA are given. The examples are
  not exhaustive
  [WEAK]
  .
- kind: Note

###### 3.8.5.3.2 (Requirement Type)
Example: Extension of MA via a main balise group in Level 1
- WordTraceId: 91597
- atomic: false
- Legal Obligation: not applicable
- implement: false
- implementerEnhanced: Example: Extension of MA via a main
  balise group
  [EXTERNAL]
  in Level 1
- kind: Example

###### 3.8.5.3.2.*[1] (Requirement Type)
by giving a new longer section, see Figure 21a
- WordTraceId: 91657
- atomic: true
- Legal Obligation: unknown
- implement: false
- ListNumberText: ·
- kind: Example
- CrossRefLink -> 3.8.5.3.2.*[2][2].[f]21a.C

###### 3.8.5.3.2.*[2] (Requirement Type)
by giving a first section to the same location as in the previous MA and a second section, see Figure 21b
- WordTraceId: 91705
- atomic: true
- Legal Obligation: unknown
- implement: false
- ListNumberText: ·
- kind: Example
- CrossRefLink -> 3.8.5.3.2.*[2][3].[f]21b.C

###### 3.8.5.3.2.*[2][2] (Requirement Type)
- WordTraceId: 91811
- atomic: false
- Legal Obligation: not applicable
- implement: false
- kind: Placeholder

###### 3.8.5.3.2.*[2][2].[f]21a (Requirement Type)
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- WordTraceId: 91836
- atomic: false
- Legal Obligation: not applicable
- implement: false
- kind: Figure

###### 3.8.5.3.2.*[2][2].[f]21a.C (Requirement Type)
Figure 21a: Extension of an MA in Level 1, one section in the new MA
- WordTraceId: 91836
- atomic: true
- Legal Obligation: unknown
- implement: false
- kind: Figure

###### 3.8.5.3.2.*[2][3] (Requirement Type)
- WordTraceId: 91905
- atomic: false
- Legal Obligation: not applicable
- implement: false
- kind: Placeholder

###### 3.8.5.3.2.*[2][3].[f]21b (Requirement Type)
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- WordTraceId: 91930
- atomic: false
- Legal Obligation: not applicable
- implement: false
- kind: Figure

###### 3.8.5.3.2.*[2][3].[f]21b.C (Requirement Type)
Figure {Figure 21}b: Extension of an MA in level 1, two sections in the new MA
- WordTraceId: 91930
- atomic: true
- Legal Obligation: unknown
- PlainText: Figure 21b: Extension of an MA in level 1, two sections in the new MA
- implement: false
- kind: Figure

###### 3.8.5.3.3 (Requirement Type)
Example: MA update via infill information in Level 1. (Refer to section 3.6.2.3 for location reference of infill information)
- WordTraceId: 92027
- atomic: false
- Legal Obligation: not applicable
- implement: false
- kind: Example
- CrossRefLink -> 3.6.2.3

###### 3.8.5.3.3.*[1] (Requirement Type)
MA extension, by giving two new sections, see Figure 22a
- WordTraceId: 92182
- atomic: true
- Legal Obligation: unknown
- implement: false
- ListNumberText: ·
- kind: Example
- CrossRefLink -> 3.8.5.3.3[2].[f]22a.C

###### 3.8.5.3.3.*[2] (Requirement Type)
MA shortening, see Figure 22b
- WordTraceId: 92239
- atomic: true
- Legal Obligation: unknown
- implement: false
- ListNumberText: ·
- kind: Example
- CrossRefLink -> 3.8.5.3.3[3].[f]22b.C

###### 3.8.5.3.3.*[3] (Requirement Type)
MA repetition, see Figure 22c
- WordTraceId: 92269
- atomic: true
- Legal Obligation: unknown
- implement: false
- implementerEnhanced: MA
  repetition
  [LOOP]
  , see Figure 22c
- ListNumberText: ·
- kind: Example
- CrossRefLink -> 3.8.5.3.3[4].[f]22c.C

###### 3.8.5.3.3[2] (Requirement Type)
- WordTraceId: 92301
- atomic: false
- Legal Obligation: not applicable
- implement: false
- kind: Placeholder

###### 3.8.5.3.3[2].[f]22a (Requirement Type)
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- WordTraceId: 92326
- atomic: false
- Legal Obligation: not applicable
- implement: false
- kind: Figure

###### 3.8.5.3.3[2].[f]22a.C (Requirement Type)
Figure {Figure 22}a: Extension of an MA with Infill information
- WordTraceId: 92326
- atomic: true
- Legal Obligation: unknown
- PlainText: Figure 22a: Extension of an MA with Infill information
- implement: false
- kind: Figure

###### 3.8.5.3.3[3] (Requirement Type)
- WordTraceId: 92406
- atomic: false
- Legal Obligation: not applicable
- implement: false
- kind: Placeholder

###### 3.8.5.3.3[3].[f]22b (Requirement Type)
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- WordTraceId: 92429
- atomic: false
- Legal Obligation: not applicable
- implement: false
- kind: Figure

###### 3.8.5.3.3[3].[f]22b.C (Requirement Type)
Figure 22b: Shortening of an MA with Infill information
- WordTraceId: 92429
- atomic: true
- Legal Obligation: unknown
- implement: false
- kind: Figure

###### 3.8.5.3.3[4] (Requirement Type)
- WordTraceId: 92486
- atomic: false
- Legal Obligation: not applicable
- implement: false
- kind: Placeholder

###### 3.8.5.3.3[4].[f]22c (Requirement Type)
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- WordTraceId: 92509
- atomic: false
- Legal Obligation: not applicable
- implement: false
- kind: Figure

###### 3.8.5.3.3[4].[f]22c.C (Requirement Type)
Figure 22c: Repetition of an MA with Infill information
- WordTraceId: 92509
- atomic: true
- Legal Obligation: unknown
- implement: false
- implementerEnhanced: Figure 22c:
  Repetition
  [LOOP]
  of an MA with Infill information
- kind: Figure

###### 3.8.5.3.4 (Requirement Type)
Example: Extension of MA in Levels 2 and 3
- WordTraceId: 92566
- atomic: false
- Legal Obligation: not applicable
- implement: false
- kind: Example

###### 3.8.5.3.4.*[1] (Requirement Type)
by using the same LRBG as in previous MA, see Figure 23a
- WordTraceId: 92609
- atomic: true
- Legal Obligation: unknown
- implement: false
- implementerEnhanced: by using the same
  LRBG
  [EXTERNAL]
  as in previous MA, see Figure 23a
- ListNumberText: ·
- kind: Example
- CrossRefLink -> 3.8.5.3.4.*[2][2].[f]23a.C

###### 3.8.5.3.4.*[2] (Requirement Type)
by using a new LRBG, see Figure 23b
- WordTraceId: 92666
- atomic: true
- Legal Obligation: unknown
- implement: false
- implementerEnhanced: by using a new
  LRBG
  [EXTERNAL]
  , see Figure 23b
- ListNumberText: ·
- kind: Example
- CrossRefLink -> 3.8.5.3.4.*[2][3].[f]23b.C

###### 3.8.5.3.4.*[2][2] (Requirement Type)
- WordTraceId: 92703
- atomic: false
- Legal Obligation: not applicable
- implement: false
- kind: Placeholder

###### 3.8.5.3.4.*[2][2].[f]23a (Requirement Type)
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- WordTraceId: 92728
- atomic: false
- Legal Obligation: not applicable
- implement: false
- kind: Figure

###### 3.8.5.3.4.*[2][2].[f]23a.C (Requirement Type)
Figure {Figure 23}a: Extension of an MA in level 2/3, using same LRBG
- WordTraceId: 92728
- atomic: true
- Legal Obligation: unknown
- PlainText: Figure 23a: Extension of an MA in level 2/3, using same LRBG
- implement: false
- implementerEnhanced: Figure 23a: Extension of an MA in level 2/3, using same
  LRBG
  [EXTERNAL]
- kind: Figure

###### 3.8.5.3.4.*[2][3] (Requirement Type)
- WordTraceId: 92814
- atomic: false
- Legal Obligation: not applicable
- implement: false
- kind: Placeholder

###### 3.8.5.3.4.*[2][3].[f]23b (Requirement Type)
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- WordTraceId: 92839
- atomic: false
- Legal Obligation: not applicable
- implement: false
- kind: Figure

###### 3.8.5.3.4.*[2][3].[f]23b.C (Requirement Type)
Figure 23b: Extension of an MA in Level 2/3, using a new LRBG
- WordTraceId: 92839
- atomic: true
- Legal Obligation: unknown
- implement: false
- implementerEnhanced: Figure 23b: Extension of an MA in Level 2/3, using a new
  LRBG
  [EXTERNAL]
- kind: Figure

###### 3.8.5.3.5 (Requirement Type)
Example: Extension of MA in level 1 using a balise group containing repositioning information.
- WordTraceId: 92901
- atomic: false
- Legal Obligation: not applicable
- implement: false
- implementerEnhanced: Example: Extension of MA in level 1 using a
  balise group
  [EXTERNAL]
  containing repositioning information.
- kind: Example

###### 3.8.5.3.5.1 (Requirement Type)
Note: In some existing systems, information about the locked route is not complete.
- WordTraceId: 92996
- atomic: false
- Legal Obligation: not applicable
- implement: false
- kind: Note

###### 3.8.5.3.5.2 (Requirement Type)
History of the situation (refer to the figure below):
- WordTraceId: 93080
- atomic: true
- Legal Obligation: unknown
- implement: false
- implementerEnhanced: History of the situation (refer to the figure
  below
  [WEAK]
  ):
- kind: Example

###### 3.8.5.3.5.2.a (Requirement Type)
Signal A gives an aspect to proceed up to signal Cx because it has received information about the locked route.
- WordTraceId: 93134
- atomic: true
- Legal Obligation: unknown
- implement: false
- ListNumberText: a)
- kind: Example

###### 3.8.5.3.5.2.b (Requirement Type)
Signal A can determine whether track 3 or track 1 / 2 is locked but is unable to distinguish between track 1 and 2.
- WordTraceId: 93246
- atomic: true
- Legal Obligation: unknown
- implement: false
- implementerEnhanced: Signal A can determine
  whether
  [CONDITION]
  track 3 or track 1 / 2 is locked but is unable to distinguish between track 1 and 2.
- ListNumberText: b)
- kind: Example

###### 3.8.5.3.5.2.c (Requirement Type)
In the situation described the route is set to track 1 or 2.
- WordTraceId: 93362
- atomic: true
- Legal Obligation: unknown
- implement: false
- ListNumberText: c)
- kind: Example

###### 3.8.5.3.5.2[2] (Requirement Type)
- WordTraceId: 93424
- atomic: false
- Legal Obligation: not applicable
- implement: false
- kind: Placeholder

###### 3.8.5.3.5.2[2].[f]24 (Requirement Type)
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- WordTraceId: 93449
- atomic: false
- Legal Obligation: not applicable
- implement: false
- kind: Figure

###### 3.8.5.3.5.2[2].[f]24.C (Requirement Type)
Figure {Figure 24}: Information on set route not complete at signal A
- WordTraceId: 93449
- atomic: true
- Legal Obligation: unknown
- PlainText: Figure 24: Information on set route not complete at signal A
- implement: false
- kind: Figure

###### 3.8.5.3.5.3 (Requirement Type)
In balise group A the following information is given:
- WordTraceId: 93536
- atomic: true
- Legal Obligation: unknown
- implement: false
- implementerEnhanced: In
  balise group
  [EXTERNAL]
  A the following information is given:
- kind: Example

###### 3.8.5.3.5.3.a (Requirement Type)
The most restrictive track description from all routes (which could be a combination from the routes);
- WordTraceId: 93590
- atomic: true
- Legal Obligation: unknown
- implement: false
- ListNumberText: a)
- kind: Example

###### 3.8.5.3.5.3.b (Requirement Type)
The linking distance given to the farthest balise group containing repositioning information, the identification of the repositioning balise group is not known;
- WordTraceId: 93693
- atomic: true
- Legal Obligation: unknown
- implement: false
- implementerEnhanced: The linking distance given to the farthest
  balise group
  [EXTERNAL]
  containing repositioning information, the identification of the repositioning
  balise group
  [EXTERNAL]
  is not known;
- ListNumberText: b)
- kind: Example

###### 3.8.5.3.5.3.c (Requirement Type)
For a given aspect of signal A, the most restrictive MA from all routes (the shortest sections from the routes and the lowest target speed at the End Of Authority);
- WordTraceId: 93854
- atomic: true
- Legal Obligation: unknown
- implement: false
- ListNumberText: c)
- kind: Example

###### 3.8.5.3.5.3.d (Requirement Type)
If some sections are time limited, the most restrictive timer.
- WordTraceId: 94019
- atomic: true
- Legal Obligation: unknown
- implement: false
- implementerEnhanced: If
  [CONDITION]
  some sections are
  time
  [TIME]
  limited, the most restrictive
  timer
  [TIME]
  .
- ListNumberText: d)
- kind: Example

###### 3.8.5.3.5.4 (Requirement Type)
Balise groups B (B
1
or B
2
) give the following static information:
- WordTraceId: 94082
- atomic: true
- Legal Obligation: unknown
- PlainText: Balise groups B (B1 or B2) give the following static information:
- implement: false
- implementerEnhanced: Balise groups
  [EXTERNAL]
  B (B1 or B2) give the following static information:
- kind: Example

###### 3.8.5.3.5.4.a (Requirement Type)
This is repositioning information
- WordTraceId: 94148
- atomic: true
- Legal Obligation: unknown
- implement: false
- ListNumberText: a)
- kind: Example

###### 3.8.5.3.5.4.b (Requirement Type)
Linking to the next balise group C
- WordTraceId: 94183
- atomic: true
- Legal Obligation: unknown
- implement: false
- implementerEnhanced: Linking to the next
  balise group
  [EXTERNAL]
  C
- ListNumberText: b)
- kind: Example

###### 3.8.5.3.5.4.c (Requirement Type)
The distance to the end of the current section (i.e. the distance to the end of section B1 - C1, or the distance to the end of section B2 - C2)
- WordTraceId: 94219
- atomic: true
- Legal Obligation: unknown
- implement: false
- ListNumberText: c)
- kind: Example

###### 3.8.5.3.5.4.d (Requirement Type)
The track description related to this track.
- WordTraceId: 94363
- atomic: true
- Legal Obligation: unknown
- implement: false
- ListNumberText: d)
- kind: Example

###### 3.8.5.3.5.4[2] (Requirement Type)
- WordTraceId: 94408
- atomic: false
- Legal Obligation: not applicable
- implement: false
- kind: Placeholder

###### 3.8.5.3.5.4[2].[f]25 (Requirement Type)
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- WordTraceId: 94433
- atomic: false
- Legal Obligation: not applicable
- implement: false
- kind: Figure

###### 3.8.5.3.5.4[2].[f]25.C (Requirement Type)
Figure {Figure 25}: Information contained in A and B
1
(for clarity purposes, only SSPs are drawn but the procedure has to be applied for all track description)
- WordTraceId: 94433
- atomic: true
- Legal Obligation: unknown
- PlainText: Figure 25: Information contained in A and B1 (for clarity purposes, only SSPs are drawn but the procedure has to be applied for all track description)
- implement: false
- implementerEnhanced: Figure 25: Information contained in A and B1 (for clarity purposes, only SSPs are drawn but the procedure has to be applied
  for all
  [LOOP]
  track description)
- kind: Figure

#### 3.8.6 (Requirement Type)
Co-operative shortening of MA (Level 2 and 3 only)
- WordTraceId: 94609
- atomic: false
- Legal Obligation: not applicable
- implement: false
- kind: Heading

##### 3.8.6.1 (Requirement Type)
It shall be possible to shorten a given MA using a special procedure between on-board equipment and RBC. The procedure is as follows:
- WordTraceId: 94660
- atomic: false
- Legal Obligation: mandatory
- implement: true
- implementerEnhanced: It shall be possible to shorten a given MA using a special procedure between
  on-board equipment
  [SELF]
  and
  RBC
  [EXTERNAL]
  . The procedure is as follows:
- kind: ordinary

###### 3.8.6.1.a (Requirement Type)
The RBC proposes a new MA with an EOA closer to the train than the current EOA, optionally with a mode profile.
- WordTraceId: 94794
- atomic: true
- Legal Obligation: unknown
- implement: true
- implementerEnhanced: The
  RBC
  [EXTERNAL]
  proposes a new MA with an EOA closer to the train than the current EOA, optionally with a mode profile.
- ListNumberText: a)
- kind: ordinary

###### 3.8.6.1.b (Requirement Type)
The ERTMS/ETCS on-board equipment shall check the train front end position versus the Indication supervision limit of the proposed shortened MA.
- WordTraceId: 94906
- atomic: true
- Legal Obligation: mandatory
- implement: true
- implementerEnhanced: The
  ERTMS/ETCS on-board equipment
  [SELF]
  shall check the train front end position versus the Indication supervision limit of the proposed shortened MA.
- ListNumberText: b)
- kind: ordinary

###### 3.8.6.1.b.*[1] (Requirement Type)
If it is in rear, the on-board equipment shall accept the new MA.
- WordTraceId: 95051
- atomic: true
- Legal Obligation: mandatory
- implement: true
- implementerEnhanced: If
  [CONDITION]
  it is in rear, the
  on-board equipment
  [SELF]
  shall accept the new MA.
- ListNumberText: ·
- kind: ordinary

###### 3.8.6.1.b.*[2] (Requirement Type)
If it is in advance, the request shall be rejected and the previously received MA remains valid
- WordTraceId: 95117
- atomic: true
- Legal Obligation: mandatory
- implement: true
- implementerEnhanced: If
  [CONDITION]
  it is in advance, the request shall be rejected and the previously received MA remains valid
- ListNumberText: ·
- kind: ordinary

###### 3.8.6.1.c (Requirement Type)
The RBC shall be informed about the decision.
- WordTraceId: 95213
- atomic: true
- Legal Obligation: mandatory
- implement: true
- implementerEnhanced: The
  RBC
  [EXTERNAL]
  shall be informed about the decision.
- ListNumberText: c)
- kind: ordinary

##### 3.8.6.2 (Requirement Type)
If the request from the RBC is granted by the on-board, refer to appendix A.3.4 for the exhaustive list of location based information, which shall be deleted accordingly.
- WordTraceId: 95259
- atomic: true
- Legal Obligation: mandatory
- implement: true
- implementerEnhanced: If
  [CONDITION]
  the request from the
  RBC
  [EXTERNAL]
  is granted by the on-board, refer to appendix A.3.4 for the exhaustive list of location based information, which shall be deleted accordingly.
- kind: ordinary
- CrossRefLink -> A.3.4

### 3.9 (Requirement Type)
Means to transmit Infill information (Level 1 only)
- WordTraceId: 95430
- atomic: false
- Legal Obligation: not applicable
- implement: false
- kind: Heading

#### 3.9.1 (Requirement Type)
General
- WordTraceId: 95482
- atomic: false
- Legal Obligation: not applicable
- implement: false
- kind: Heading

##### 3.9.1.1 (Requirement Type)
It shall be possible to transmit infill information to the on-board equipment using
- WordTraceId: 95490
- atomic: true
- Legal Obligation: mandatory
- implement: true
- implementerEnhanced: It shall be possible to transmit infill information to the
  on-board equipment
  [SELF]
  using
- kind: ordinary

###### 3.9.1.1.a (Requirement Type)
Balise groups
- WordTraceId: 95574
- atomic: true
- Legal Obligation: unknown
- implement: true
- implementerEnhanced: Balise groups
  [EXTERNAL]
- ListNumberText: a)
- kind: ordinary

###### 3.9.1.1.b (Requirement Type)
Euroloops
- WordTraceId: 95588
- atomic: true
- Legal Obligation: unknown
- implement: true
- implementerEnhanced: Euroloops
  [EXTERNAL]
- ListNumberText: b)
- kind: ordinary

###### 3.9.1.1.c (Requirement Type)
Radio infill units.
- WordTraceId: 95598
- atomic: true
- Legal Obligation: unknown
- implement: true
- ListNumberText: c)
- kind: ordinary

###### 3.9.1.1.1 (Requirement Type)
Note: If the information transmitted by Balise groups, Euroloops, and Radio includes infill information, those devices are also identified as infill devices.
- WordTraceId: 95618
- atomic: false
- Legal Obligation: not applicable
- implement: false
- implementerEnhanced: Note:
  If
  [CONDITION]
  the information transmitted by
  Balise groups
  [EXTERNAL]
  ,
  Euroloops
  [EXTERNAL]
  , and Radio includes infill information, those devices are also identified as infill devices.
- kind: Note

##### 3.9.1.2 (Requirement Type)
The principle used for the infill information shall be the same independent of transmission media.
- WordTraceId: 95776
- atomic: true
- Legal Obligation: mandatory
- implement: true
- kind: ordinary

##### 3.9.1.3 (Requirement Type)
If the on-board system is not equipped with the infill transmission media as requested by the announcement balise group, the announcement information shall be ignored by the on-board equipment and the train shall proceed according to the previously received information.
- WordTraceId: 95875
- atomic: false
- Legal Obligation: mandatory
- implement: true
- implementerEnhanced: If
  [CONDITION]
  the on-board system is not equipped with the infill transmission media as requested by the announcement
  balise group
  [EXTERNAL]
  , the announcement information shall be ignored by the
  on-board equipment
  [SELF]
  and the train shall proceed according to the previously received information.
- kind: ordinary

##### 3.9.1.4 (Requirement Type)
Note: No additional description is needed for infill by balise group (other than already covered in previous chapters).
- WordTraceId: 96147
- atomic: false
- Legal Obligation: not applicable
- implement: false
- implementerEnhanced: Note: No additional description is needed for infill by
  balise group
  [EXTERNAL]
  (other than already covered in previous chapters).
- kind: Note

#### 3.9.2 (Requirement Type)
Infill by loop
- WordTraceId: 96267
- atomic: false
- Legal Obligation: not applicable
- implement: false
- implementerEnhanced: Infill by
  loop
  [EXTERNAL]
- kind: Heading

##### 3.9.2.1 (Requirement Type)
An End Of Loop Marker (EOLM) is by definition a device to mark the beginning or the end of a loop. When receiv​ing this information, the on-board equipment knows that it is entering/leav​ing a track equipped with a loop. In unidirectional applications it shall be possible to have an EOLM only at the entry side of a loop.
- WordTraceId: 96282
- atomic: false
- Legal Obligation: mandatory
- implement: true
- implementerEnhanced: An End Of
  Loop
  [EXTERNAL]
  Marker (EOLM) is by definition a device to mark the beginning or the end of a
  loop
  [EXTERNAL]
  .
  When
  [CONDITION]
  receiv​ing this information, the
  on-board equipment
  [SELF]
  knows that it is entering/leav​ing a track equipped with a
  loop
  [EXTERNAL]
  . In unidirectional applications it shall be possible to have an EOLM only at the entry side of a
  loop
  [EXTERNAL]
  .
- kind: ordinary

##### 3.9.2.2 (Requirement Type)
Balise groups shall be used as EOLMs. They act as an EOLM by sending the EOLM information to the passing train.
- WordTraceId: 96605
- atomic: false
- Legal Obligation: mandatory
- implement: true
- implementerEnhanced: Balise groups
  [EXTERNAL]
  shall be used as EOLMs. They act as an EOLM by sending the EOLM information to the passing train.
- kind: ordinary

##### 3.9.2.3 (Requirement Type)
EOLMs have an orientation that is identical to the balise group orientation. The general rules for balise orientation therefore also apply to EOLMs.
- WordTraceId: 96718
- atomic: false
- Legal Obligation: unknown
- implement: true
- implementerEnhanced: EOLMs have an orientation that is identical to the
  balise group
  [EXTERNAL]
  orientation. The general rules for
  balise
  [EXTERNAL]
  orientation therefore also apply to EOLMs.
- kind: ordinary

##### 3.9.2.4 (Requirement Type)
EOLM information might be contained in a balise group that contains other information.
- WordTraceId: 96868
- atomic: true
- Legal Obligation: unknown
- implement: true
- implementerEnhanced: EOLM information might be contained in a
  balise group
  [EXTERNAL]
  that contains other information.
- kind: ordinary

##### 3.9.2.5 (Requirement Type)
The EOLM shall send the identity of the announced loop.
- WordTraceId: 96956
- atomic: true
- Legal Obligation: mandatory
- implement: true
- implementerEnhanced: The EOLM shall send the identity of the announced
  loop
  [EXTERNAL]
  .
- kind: ordinary

##### 3.9.2.6 (Requirement Type)
The on-board shall only accept information coming from the loop with the announced identity.
- WordTraceId: 97012
- atomic: true
- Legal Obligation: mandatory
- implement: true
- implementerEnhanced: The on-board shall only accept information coming from the
  loop
  [EXTERNAL]
  with the announced identity.
- kind: ordinary

##### 3.9.2.7 (Requirement Type)
Deleted.
- WordTraceId: 97106
- atomic: false
- Legal Obligation: not applicable
- implement: false
- kind: Placeholder

##### 3.9.2.8 (Requirement Type)
Deleted.
- WordTraceId: 97115
- atomic: false
- Legal Obligation: not applicable
- implement: false
- kind: Placeholder

##### 3.9.2.9 (Requirement Type)
The following information shall be sent in advance by the EOLM to prepare for reception of the loop information:
- WordTraceId: 97125
- atomic: true
- Legal Obligation: not applicable
- implement: false
- implementerEnhanced: The following information shall be sent in advance by the EOLM to prepare for reception of the
  loop
  [EXTERNAL]
  information:
- kind: Heading

###### 3.9.2.9.*[1] (Requirement Type)
Loop identity used to identify the loop.
- WordTraceId: 97238
- atomic: true
- Legal Obligation: mandatory
- implement: true
- implementerEnhanced: Loop
  [EXTERNAL]
  identity used to identify the
  loop
  [EXTERNAL]
  .
- ListNumberText: ·
- kind: ordinary

###### 3.9.2.9.*[2] (Requirement Type)
Key to select the spread spectrum key necessary to receive the loop telegrams.
- WordTraceId: 97280
- atomic: true
- Legal Obligation: mandatory
- implement: true
- ListNumberText: ·
- kind: ordinary

###### 3.9.2.9.*[3] (Requirement Type)
Distance to the loop giving the distance from the EOLM to the location from where on loop messages can be received.
- WordTraceId: 97359
- atomic: true
- Legal Obligation: mandatory
- implement: true
- implementerEnhanced: Distance to the
  loop
  [EXTERNAL]
  giving the distance from the EOLM to the location from where on
  loop
  [EXTERNAL]
  messages can be received.
- ListNumberText: ·
- kind: ordinary

###### 3.9.2.9.*[4] (Requirement Type)
Length of the loop giving the length of the loop over which messages can be received.
- WordTraceId: 97476
- atomic: true
- Legal Obligation: mandatory
- implement: true
- implementerEnhanced: Length of the
  loop
  [EXTERNAL]
  giving the length of the
  loop
  [EXTERNAL]
  over which messages can be received.
- ListNumberText: ·
- kind: ordinary

###### 3.9.2.9.*[5] (Requirement Type)
Indicator telling the on-board whether the orientation of the loop is identical or reverse to the orientation of the announcing EOLM.
- WordTraceId: 97563
- atomic: true
- Legal Obligation: mandatory
- implement: true
- implementerEnhanced: Indicator telling the on-board
  whether
  [CONDITION]
  the orientation of the
  loop
  [EXTERNAL]
  is identical or reverse to the orientation of the announcing EOLM.
- ListNumberText: ·
- kind: ordinary

##### 3.9.2.10 (Requirement Type)
The on-board shall be prepared to receive messages from the Euroloop after passing the EOLM.
- WordTraceId: 97698
- atomic: true
- Legal Obligation: mandatory
- implement: true
- implementerEnhanced: The on-board shall be prepared to receive messages from the
  Euroloop
  [EXTERNAL]
  after
  [TIME]
  passing the EOLM.
- kind: ordinary

##### 3.9.2.11 (Requirement Type)
When the on-board equipment reads the next main signal balise group or when it detects that the next main signal balise group was missed, new infill information possibly received from the loop shall be ignored.
- WordTraceId: 97791
- atomic: true
- Legal Obligation: mandatory
- implement: true
- implementerEnhanced: When
  [CONDITION]
  the
  on-board equipment
  [SELF]
  reads the next main signal
  balise group
  [EXTERNAL]
  or
  when
  [CONDITION]
  it detects that the next main signal
  balise group
  [EXTERNAL]
  was missed, new infill information
  possibly
  [WEAK]
  received from the
  loop
  [EXTERNAL]
  shall be ignored.
- kind: ordinary

##### 3.9.2.12 (Requirement Type)
The distances given in an EOLM (distance to loop, length of loop) are used for diagnostic purpose only. They shall therefore not be used to restrict reception of loop telegrams to specific locations.
- WordTraceId: 98002
- atomic: false
- Legal Obligation: mandatory
- implement: true
- implementerEnhanced: The distances given in an EOLM (distance to
  loop
  [EXTERNAL]
  , length of
  loop
  [EXTERNAL]
  ) are used for diagnostic purpose only. They shall therefore not be used to restrict reception of loop telegrams to specific locations.
- kind: ordinary

#### 3.9.3 (Requirement Type)
Infill by radio
- WordTraceId: 98202
- atomic: false
- Legal Obligation: not applicable
- implement: false
- kind: Heading

##### 3.9.3.1 (Requirement Type)
In level 1 areas it shall be possible to send to the on-board equipment orders to establish/terminate a communication session with a radio infill unit.
- WordTraceId: 98218
- atomic: true
- Legal Obligation: mandatory
- implement: true
- implementerEnhanced: In level 1 areas it shall be possible to send to the
  on-board equipment
  [SELF]
  orders to establish/terminate a communication session with a
  radio infill unit
  [EXTERNAL]
  .
- kind: ordinary

##### 3.9.3.2 (Requirement Type)
The orders shall be sent via balise groups or via Radio Infill units.
- WordTraceId: 98371
- atomic: true
- Legal Obligation: mandatory
- implement: true
- implementerEnhanced: The orders shall be sent via
  balise groups
  [EXTERNAL]
  or via Radio Infill units.
- kind: ordinary

##### 3.9.3.3 (Requirement Type)
The order to establish a communication session shall be ignored:
- WordTraceId: 98441
- atomic: true
- Legal Obligation: mandatory
- implement: true
- kind: ordinary

###### 3.9.3.3.a (Requirement Type)
Intentionally deleted.
- WordTraceId: 98506
- atomic: false
- Legal Obligation: not applicable
- implement: false
- ListNumberText: a)
- kind: Placeholder

###### 3.9.3.3.b (Requirement Type)
If the on-board equipment does not include radio.
- WordTraceId: 98530
- atomic: true
- Legal Obligation: unknown
- implement: true
- implementerEnhanced: If
  [CONDITION]
  the
  on-board equipment
  [SELF]
  does not include radio.
- ListNumberText: b)
- kind: ordinary

##### 3.9.3.4 (Requirement Type)
If the on-board equipment includes radio, the communication session shall be established using the same protocols and interfaces as for Level 2/3 operations.
- WordTraceId: 98581
- atomic: true
- Legal Obligation: mandatory
- implement: true
- implementerEnhanced: If
  [CONDITION]
  the
  on-board equipment
  [SELF]
  includes radio, the communication session shall be established using the same protocols and interfaces as for Level 2/3 operations.
- kind: ordinary

##### 3.9.3.5 (Requirement Type)
If the order to establish a communication session with a radio infill unit sent via balise groups is received by an on-board equipment, connected with another radio infill unit(s), two cases may arise:
- WordTraceId: 98740
- atomic: true
- Legal Obligation: optional
- implement: true
- implementerEnhanced: If
  [CONDITION]
  the order to establish a communication session with a
  radio infill unit
  [EXTERNAL]
  sent via
  balise groups
  [EXTERNAL]
  is received by an
  on-board equipment
  [SELF]
  , connected with another radio infill unit(s), two cases may arise:
- kind: ordinary

###### 3.9.3.5.1 (Requirement Type)
Case 1: the on-board can handle only one communication session at a time. In this case, the onboard shall (unless §3.9.3.5.1.1 applies):
- WordTraceId: 98942
- atomic: false
- Legal Obligation: mandatory
- implement: true
- implementerEnhanced: Case 1: the on-board can handle only one communication session at a
  time
  [TIME]
  . In this case, the onboard shall (unless §3.9.3.5.1.1 applies):
- kind: ordinary
- CrossRefLink -> 3.9.3.5.1.1

###### 3.9.3.5.1.a (Requirement Type)
terminate the existing communication session at the location indicated in the order
- WordTraceId: 99079
- atomic: true
- Legal Obligation: unknown
- implement: true
- ListNumberText: a)
- kind: ordinary

###### 3.9.3.5.1.b (Requirement Type)
establish a communication session with the RIU indicated in the order as soon as action a) is completed.
- WordTraceId: 99163
- atomic: true
- Legal Obligation: unknown
- implement: true
- implementerEnhanced: establish a communication session with the
  RIU
  [EXTERNAL]
  indicated in the order
  as soon as
  [WEAK]
  action a) is completed.
- ListNumberText: b)
- kind: ordinary

###### 3.9.3.5.1.1 (Requirement Type)
The order shall be ignored in case it refers to an RIU with which a session is currently being established or is already established.
- WordTraceId: 99268
- atomic: true
- Legal Obligation: mandatory
- implement: true
- implementerEnhanced: The order shall be ignored
  in case
  [CONDITION]
  it refers to an
  RIU
  [EXTERNAL]
  with which a session is currently being established or is already established.
- kind: ordinary

###### 3.9.3.5.2 (Requirement Type)
Case 2: the on-board can handle more than one communication session at a time. In this case, at the location indicated in the order the on-board shall:
- WordTraceId: 99402
- atomic: false
- Legal Obligation: not applicable
- implement: false
- implementerEnhanced: Case 2: the on-board can handle more than one communication session at a
  time
  [TIME]
  . In this case, at the location indicated in the order the on-board shall:
- kind: Heading

###### 3.9.3.5.2.a (Requirement Type)
terminate any communication session existing with RIU(s) not indicated in the order
- WordTraceId: 99554
- atomic: true
- Legal Obligation: mandatory
- implement: true
- ListNumberText: a)
- kind: ordinary

###### 3.9.3.5.2.b (Requirement Type)
as soon as a new communication session can be handled, establish a communication session with the RIU indicated in the order, unless currently being established or already established with the said RIU.
- WordTraceId: 99638
- atomic: true
- Legal Obligation: mandatory
- implement: true
- implementerEnhanced: as soon as
  [WEAK]
  a new communication session can be handled, establish a communication session with the
  RIU
  [EXTERNAL]
  indicated in the order, unless currently being established or already established with the said
  RIU
  [EXTERNAL]
  .
- ListNumberText: b)
- kind: ordinary

##### 3.9.3.6 (Requirement Type)
If the order to establish a communication session with a radio infill unit sent via Radio Infill unit is received by an on-board equipment:
- WordTraceId: 99841
- atomic: true
- Legal Obligation: unknown
- implement: true
- implementerEnhanced: If
  [CONDITION]
  the order to establish a communication session with a
  radio infill unit
  [EXTERNAL]
  sent via
  Radio Infill unit
  [EXTERNAL]
  is received by an
  on-board equipment
  [SELF]
  :
- kind: ordinary

###### 3.9.3.6.a (Requirement Type)
If the on-board can handle only one communication session, the order shall be ignored.
- WordTraceId: 99981
- atomic: true
- Legal Obligation: mandatory
- implement: true
- implementerEnhanced: If
  [CONDITION]
  the on-board can handle only one communication session, the order shall be ignored.
- ListNumberText: a)
- kind: ordinary

###### 3.9.3.6.b (Requirement Type)
If the on-board can handle two communication sessions simultaneously and only one session is ongoing, the existing communication session shall be maintained and the new one shall be established.
- WordTraceId: 100068
- atomic: false
- Legal Obligation: mandatory
- implement: true
- implementerEnhanced: If
  [CONDITION]
  the on-board can handle two communication sessions simultaneously and only one session is ongoing, the existing communication session shall be maintained and the new one shall be established.
- ListNumberText: b)
- kind: ordinary

###### 3.9.3.6.c (Requirement Type)
If the on-board can handle two communication sessions simultaneously and two sessions are ongoing, then the communication session related to the current infill area shall be maintained, the other one shall be terminated and the new one shall be established.
- WordTraceId: 100263
- atomic: false
- Legal Obligation: mandatory
- implement: true
- implementerEnhanced: If
  [CONDITION]
  the on-board can handle two communication sessions simultaneously and two sessions are ongoing, then the communication session related to the current infill area shall be maintained, the other one shall be terminated and the new one shall be established.
- ListNumberText: c)
- kind: ordinary

##### 3.9.3.7 (Requirement Type)
A Radio Infill Unit shall not initiate a communication session with an on-board equipment.
- WordTraceId: 100521
- atomic: true
- Legal Obligation: mandatory
- implement: true
- implementerEnhanced: A
  Radio Infill Unit
  [EXTERNAL]
  shall not initiate a communication session with an
  on-board equipment
  [SELF]
  .
- kind: ordinary

##### 3.9.3.8 (Requirement Type)
The order to establish/terminate a communication session sent via balise groups shall be sent together with the following radio infill area information:
- WordTraceId: 100612
- atomic: true
- Legal Obligation: not applicable
- implement: false
- implementerEnhanced: The order to establish/terminate a communication session sent via
  balise groups
  [EXTERNAL]
  shall be sent together with the following radio infill area information:
- kind: Heading

###### 3.9.3.8.a (Requirement Type)
Location where to perform the action (referred to the balise group containing the order).Note: if the action is to establish a communication session, this location marks the beginning of the Radio Infill Area.
- WordTraceId: 100765
- atomic: true
- Legal Obligation: mandatory
- implement: true
- implementerEnhanced: Location where to perform the action (referred to the
  balise group
  [EXTERNAL]
  containing the order).Note:
  if
  [CONDITION]
  the action is to establish a communication session, this location marks the beginning of the Radio Infill Area.
- ListNumberText: a)
- kind: ordinary

###### 3.9.3.8.b (Requirement Type)
Next main signal balise group identifier (ignored by the on-board if the action is Terminate communication session).Note: the reference location of this balise group marks the end of the Radio Infill Area.
- WordTraceId: 100975
- atomic: true
- Legal Obligation: mandatory
- implement: true
- implementerEnhanced: Next main signal
  balise group
  [EXTERNAL]
  identifier (ignored by the on-board
  if
  [CONDITION]
  the action is Terminate communication session).Note: the reference location of this
  balise group
  [EXTERNAL]
  marks the end of the Radio Infill Area.
- ListNumberText: b)
- kind: ordinary

###### 3.9.3.8.1 (Requirement Type)
The order to establish/terminate a communication session sent via Radio Infill units (see 3.5.3.6) shall not be sent together with any radio infill area information.
- WordTraceId: 101181
- atomic: true
- Legal Obligation: mandatory
- implement: true
- kind: ordinary
- CrossRefLink -> 3.5.3.6

##### 3.9.3.9 (Requirement Type)
The establishment of a communication session for radio infill shall not change the operational level of the on-board i.e. the information in the balise group shall be taken into account as usual in level 1.
- WordTraceId: 101347
- atomic: false
- Legal Obligation: mandatory
- implement: true
- implementerEnhanced: The establishment of a communication session for radio infill shall not change the operational level of the on-board i.e. the information in the
  balise group
  [EXTERNAL]
  shall be taken into account as usual in level 1.
- kind: ordinary

##### 3.9.3.10 (Requirement Type)
The on-board equipment shall inform the radio infill unit
- WordTraceId: 101555
- atomic: true
- Legal Obligation: mandatory
- implement: true
- implementerEnhanced: The
  on-board equipment
  [SELF]
  shall inform the
  radio infill unit
  [EXTERNAL]
- kind: ordinary

###### 3.9.3.10.a (Requirement Type)
As soon as the location indicated in the order sent via balise groups is passed (i.e. entry of the train in the infill area)
- WordTraceId: 101613
- atomic: true
- Legal Obligation: unknown
- implement: true
- implementerEnhanced: As soon as
  [WEAK]
  the location indicated in the order sent via
  balise groups
  [EXTERNAL]
  is passed (i.e. entry of the train in the infill area)
- ListNumberText: a)
- kind: ordinary

###### 3.9.3.10.b (Requirement Type)
As soon as the next main signal balise group indicated in the order sent via balise groups is read or the on-board equipment detects that it was missed.
- WordTraceId: 101738
- atomic: true
- Legal Obligation: unknown
- implement: true
- implementerEnhanced: As soon as
  [WEAK]
  the next main signal
  balise group
  [EXTERNAL]
  indicated in the order sent via
  balise groups
  [EXTERNAL]
  is read or the
  on-board equipment
  [SELF]
  detects that it was missed.
- ListNumberText: b)
- kind: ordinary

##### 3.9.3.11 (Requirement Type)
The information sent to the radio infill unit by the on-board equipment shall include
- WordTraceId: 101892
- atomic: true
- Legal Obligation: mandatory
- implement: true
- implementerEnhanced: The information sent to the
  radio infill unit
  [EXTERNAL]
  by the
  on-board equipment
  [SELF]
  shall include
- kind: ordinary

###### 3.9.3.11.a (Requirement Type)
Train identity (ETCS-ID of the on-board equipment)
- WordTraceId: 101978
- atomic: true
- Legal Obligation: unknown
- implement: true
- implementerEnhanced: Train identity (ETCS-ID of the
  on-board equipment
  [SELF]
  )
- ListNumberText: a)
- kind: ordinary

###### 3.9.3.11.b (Requirement Type)
Position report
- WordTraceId: 102029
- atomic: true
- Legal Obligation: unknown
- implement: true
- ListNumberText: b)
- kind: ordinary

###### 3.9.3.11.c (Requirement Type)
Identifier of the next main signal balise group
- WordTraceId: 102045
- atomic: true
- Legal Obligation: unknown
- implement: true
- implementerEnhanced: Identifier of the next main signal
  balise group
  [EXTERNAL]
- ListNumberText: c)
- kind: ordinary

###### 3.9.3.11.d (Requirement Type)
Time stamp
- WordTraceId: 102093
- atomic: true
- Legal Obligation: unknown
- implement: true
- implementerEnhanced: Time
  [TIME]
  stamp
- ListNumberText: d)
- kind: ordinary

###### 3.9.3.11.1 (Requirement Type)
Justification:
- WordTraceId: 102104
- atomic: false
- Legal Obligation: not applicable
- implement: false
- kind: Justification

###### 3.9.3.11.1.a (Requirement Type)
The train identity is used for conformity with other train to track messages
- WordTraceId: 102120
- atomic: true
- Legal Obligation: unknown
- implement: false
- ListNumberText: a)
- kind: Justification

###### 3.9.3.11.1.b (Requirement Type)
The identifier of the next main signal balise group allows the radio infill unit to identify safely where the train is going, even in the case of a points area
- WordTraceId: 102197
- atomic: true
- Legal Obligation: unknown
- implement: false
- implementerEnhanced: The identifier of the next main signal
  balise group
  [EXTERNAL]
  allows the
  radio infill unit
  [EXTERNAL]
  to identify safely where the train is going, even in the case of a points area
- ListNumberText: b)
- kind: Justification

##### 3.9.3.12 (Requirement Type)
As soon as the radio infill unit is informed that a train has entered an infill area under its responsibility, it shall
- WordTraceId: 102357
- atomic: true
- Legal Obligation: not applicable
- implement: false
- implementerEnhanced: As soon as
  [WEAK]
  the
  radio infill unit
  [EXTERNAL]
  is informed that a train has entered an infill area under its responsibility, it shall
- kind: Heading

###### 3.9.3.12.a (Requirement Type)
Terminate a possible previous sending of infill information to the on-board equipment, AND
- WordTraceId: 102477
- atomic: true
- Legal Obligation: mandatory
- implement: true
- implementerEnhanced: Terminate a possible previous sending of infill information to the
  on-board equipment
  [SELF]
  , AND
- ListNumberText: a)
- kind: ordinary

###### 3.9.3.12.b (Requirement Type)
Send cyclically the infill information corresponding to the message currently sent by the next main signal balise group indicated in the information from the on-board equipment.
- WordTraceId: 102568
- atomic: true
- Legal Obligation: mandatory
- implement: true
- implementerEnhanced: Send
  cyclically
  [WEAK]
  the infill information corresponding to the message currently sent by the next main signal
  balise group
  [EXTERNAL]
  indicated in the information from the
  on-board equipment
  [SELF]
  .
- ListNumberText: b)
- kind: ordinary

###### 3.9.3.12.1 (Requirement Type)
Justification: case a) refers to the possibility that a report from the on-board equipment, after having passed the previous main signal, was lost.
- WordTraceId: 102747
- atomic: false
- Legal Obligation: mandatory
- implement: false
- implementerEnhanced: Justification: case a) refers to the possibility that a report from the
  on-board equipment
  [SELF]
  ,
  after
  [TIME]
  having passed the previous main signal, was lost.
- kind: Justification

###### 3.9.3.12.2 (Requirement Type)
Note: A Radio infill unit may manage several signals, thus several Radio Infill Areas (see Figure 25a)
- WordTraceId: 102895
- atomic: false
- Legal Obligation: mandatory
- implement: false
- implementerEnhanced: Note: A
  Radio infill unit
  [EXTERNAL]
  may manage several signals, thus several Radio Infill Areas (see Figure 25a)
- kind: Note
- CrossRefLink -> 3.9.3.12.2[2].[f]25a.C

###### 3.9.3.12.2[2] (Requirement Type)
- WordTraceId: 102998
- atomic: false
- Legal Obligation: not applicable
- implement: false
- kind: Placeholder

###### 3.9.3.12.2[2].[f]25a (Requirement Type)
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- WordTraceId: 103023
- atomic: false
- Legal Obligation: mandatory
- implement: false
- kind: Figure

###### 3.9.3.12.2[2].[f]25a.C (Requirement Type)
Figure 25a: Line equipped with radio infill. Example of radio infill area information transmitted by balise.
- WordTraceId: 103023
- atomic: false
- Legal Obligation: mandatory
- implement: false
- implementerEnhanced: Figure 25a: Line equipped with radio infill. Example of radio infill area information transmitted by
  balise
  [EXTERNAL]
  .
- kind: Figure

##### 3.9.3.13 (Requirement Type)
The radio infill unit shall terminate the sending of infill information as soon as information is received, that the on-board equipment has read the next main signal balise group indicated in the order or that the on-board equipment has detected that it was missed.
- WordTraceId: 103132
- atomic: true
- Legal Obligation: mandatory
- implement: true
- implementerEnhanced: The
  radio infill unit
  [EXTERNAL]
  shall terminate the sending of infill information
  as soon as
  [WEAK]
  information is received, that the
  on-board equipment
  [SELF]
  has read the next main signal
  balise group
  [EXTERNAL]
  indicated in the order or that the
  on-board equipment
  [SELF]
  has detected that it was missed.
- kind: ordinary

##### 3.9.3.14 (Requirement Type)
The radio infill unit shall evaluate the time stamp according to the principles of section 3.16.3.2.
The on-board equipment shall check the consistency of radio infill data, according to the principles of section 3.16.3.1 and 3.16.3.3.
- WordTraceId: 103398
- atomic: false
- Legal Obligation: mandatory
- implement: true
- implementerEnhanced: The
  radio infill unit
  [EXTERNAL]
  shall evaluate the
  time
  [TIME]
  stamp according to the principles of section 3.16.3.2. The
  on-board equipment
  [SELF]
  shall check the consistency of radio infill data, according to the principles of section 3.16.3.1 and 3.16.3.3.
- kind: ordinary
- CrossRefLink -> 3.16.3.2
- CrossRefLink -> 3.16.3.1
- CrossRefLink -> 3.16.3.3

##### 3.9.3.15 (Requirement Type)
When the on-board equipment reads the next main signal balise group or when it detects that the next main signal balise group was missed, new infill information related to this balise group possibly received shall be ignored.
- WordTraceId: 103721
- atomic: true
- Legal Obligation: mandatory
- implement: true
- implementerEnhanced: When
  [CONDITION]
  the
  on-board equipment
  [SELF]
  reads the next main signal
  balise group
  [EXTERNAL]
  or
  when
  [CONDITION]
  it detects that the next main signal
  balise group
  [EXTERNAL]
  was missed, new infill information related to this
  balise group
  [EXTERNAL]
  possibly
  [WEAK]
  received shall be ignored.
- kind: ordinary

##### 3.9.3.16 (Requirement Type)
The on-board equipment shall terminate the communication session according to the orders received from the trackside (balise group or Radio Infill units).
- WordTraceId: 103947
- atomic: true
- Legal Obligation: mandatory
- implement: true
- implementerEnhanced: The
  on-board equipment
  [SELF]
  shall
  terminate the communication session
  [LINKED_PHRASE]
  according to the orders received from the
  trackside
  [EXTERNAL]
  (
  balise group
  [EXTERNAL]
  or Radio Infill units).
- kind: ordinary
- KnownTermLink -> 3.5.4.3.*[3]

##### 3.9.3.17 (Requirement Type)
Intentionally deleted.
- WordTraceId: 104102
- atomic: false
- Legal Obligation: not applicable
- implement: false
- kind: Placeholder

### 3.10 (Requirement Type)
Emergency Messages
- WordTraceId: 104125
- atomic: false
- Legal Obligation: not applicable
- implement: false
- kind: Heading

#### 3.10.1 (Requirement Type)
General
- WordTraceId: 104144
- atomic: false
- Legal Obligation: not applicable
- implement: false
- kind: Heading

##### 3.10.1.1 (Requirement Type)
Emergency messages shall be sent individually to each on-board equipment, either as high priority data or as normal priority data of the same radio connection, as described in Euroradio specification. Only emergency messages can be sent as high priority data, not their acknowledgement or their revocation.
- WordTraceId: 104152
- atomic: false
- Legal Obligation: mandatory
- implement: true
- implementerEnhanced: Emergency messages shall be sent individually to each
  on-board equipment
  [SELF]
  , either as high priority data or as normal priority data of the same radio connection, as described in Euroradio specification. Only emergency messages can be sent as high priority data, not their acknowledgement or their revocation.
- kind: ordinary

###### 3.10.1.1.1 (Requirement Type)
Justification: In case of hazardous events, it is possible to use high priority data in the radio connection between RBC and on-board equipment to get a quick reaction.
- WordTraceId: 104459
- atomic: false
- Legal Obligation: not applicable
- implement: false
- implementerEnhanced: Justification:
  In case of
  [CONDITION]
  hazardous events, it is possible to use high priority data in the radio connection between
  RBC
  [EXTERNAL]
  and
  on-board equipment
  [SELF]
  to get a quick reaction.
- kind: Justification

##### 3.10.1.2 (Requirement Type)
An emergency message shall contain an identifier decided by the trackside.
- WordTraceId: 104629
- atomic: true
- Legal Obligation: mandatory
- implement: true
- implementerEnhanced: An emergency message shall contain an identifier decided by the
  trackside
  [EXTERNAL]
  .
- kind: ordinary

##### 3.10.1.3 (Requirement Type)
The same identifier shall be used in case the emergency message is repeated.
- WordTraceId: 104704
- atomic: true
- Legal Obligation: mandatory
- implement: true
- implementerEnhanced: The same identifier shall be used
  in case
  [CONDITION]
  the emergency message is
  repeated
  [LOOP]
  .
- kind: ordinary

###### 3.10.1.3.1 (Requirement Type)
If the on-board receives a new message with the same identifier it shall replace the previous one.
- WordTraceId: 104781
- atomic: true
- Legal Obligation: mandatory
- implement: true
- implementerEnhanced: If
  [CONDITION]
  the on-board receives a new message with the same identifier it shall replace the previous one.
- kind: ordinary

##### 3.10.1.4 (Requirement Type)
Each emergency message to an on-board equipment shall be acknowledged, using the corresponding emergency message identification number.
- WordTraceId: 104880
- atomic: true
- Legal Obligation: mandatory
- implement: true
- implementerEnhanced: Each emergency message to an
  on-board equipment
  [SELF]
  shall be acknowledged, using the corresponding emergency message identification number.
- kind: ordinary

###### 3.10.1.4.1 (Requirement Type)
Note: This acknowledgement informs the RBC about the use of the emergency message by on-board equipment and is independent from the general acknowledgement for track-to-train messages, as specified in section 3.16.3.5.
- WordTraceId: 105016
- atomic: false
- Legal Obligation: not applicable
- implement: false
- implementerEnhanced: Note: This acknowledgement informs the
  RBC
  [EXTERNAL]
  about the use of the emergency message by
  on-board equipment
  [SELF]
  and is independent from the general acknowledgement for track-to-train messages, as specified in section 3.16.3.5.
- kind: Note
- CrossRefLink -> 3.16.3.5

#### 3.10.2 (Requirement Type)
Emergency Stop
- WordTraceId: 105235
- atomic: false
- Legal Obligation: not applicable
- implement: false
- kind: Heading

##### 3.10.2.1 (Requirement Type)
It shall be possible to stop a train with a conditional or an unconditional emergency stop message.
- WordTraceId: 105251
- atomic: true
- Legal Obligation: mandatory
- implement: true
- kind: ordinary

##### 3.10.2.2 (Requirement Type)
A conditional emergency stop message shall contain the information of a new stop location, referred to the LRBG. In case, when receiving this message
- WordTraceId: 105352
- atomic: false
- Legal Obligation: mandatory
- implement: true
- implementerEnhanced: A conditional emergency stop message shall contain the information of a new stop location, referred to the
  LRBG
  [EXTERNAL]
  .
  In case
  [CONDITION]
  ,
  when
  [CONDITION]
  receiving this message
- kind: ordinary

###### 3.10.2.2.*[1] (Requirement Type)
the train has already passed with its min safe front end the new stop location, the emergency stop message shall be rejected and the RBC shall be informed.
- WordTraceId: 105502
- atomic: false
- Legal Obligation: mandatory
- implement: true
- implementerEnhanced: the train has already passed with its min safe front end the new stop location, the emergency stop message shall be rejected and the
  RBC
  [EXTERNAL]
  shall be informed.
- ListNumberText: ·
- kind: ordinary

###### 3.10.2.2.*[2] (Requirement Type)
the train has not yet passed with its min safe front end the new stop location, the emergency stop message shall be accepted, however this location shall be used by the onboard to define the new EOA and SvL only if not beyond the current EOA. Refer to appendix A.3.4 for the exhaustive list of location based information stored on-board, which shall be deleted accordingly.
- WordTraceId: 105658
- atomic: false
- Legal Obligation: mandatory
- implement: true
- implementerEnhanced: the train has
  not yet
  [TIME]
  passed with its min safe front end the new stop location, the emergency stop message shall be accepted, however this location shall be used by the onboard to define the new EOA and SvL only
  if
  [CONDITION]
  not beyond the current EOA. Refer to appendix A.3.4 for the exhaustive list of location based information stored on-board, which shall be deleted accordingly.
- ListNumberText: ·
- kind: ordinary
- CrossRefLink -> A.3.4

##### 3.10.2.3 (Requirement Type)
When receiving an unconditional emergency stop message the train shall be tripped immediately.
- WordTraceId: 106032
- atomic: true
- Legal Obligation: mandatory
- implement: true
- implementerEnhanced: When
  [CONDITION]
  receiving an unconditional emergency stop message the train shall be tripped
  immediately
  [WEAK]
  .
- kind: ordinary

##### 3.10.2.4 (Requirement Type)
New movement authority received after any accepted emergency stop message and before the emergency message has been revoked, shall be rejected.
- WordTraceId: 106127
- atomic: true
- Legal Obligation: mandatory
- implement: true
- implementerEnhanced: New movement authority received
  after
  [TIME]
  any accepted emergency stop message and before the emergency message has been revoked, shall be rejected.
- kind: ordinary

##### 3.10.2.5 (Requirement Type)
Intentionally deleted.
- WordTraceId: 106271
- atomic: false
- Legal Obligation: not applicable
- implement: false
- kind: Placeholder

##### 3.10.2.6 (Requirement Type)
The driver shall be informed when emergency stop(s) have been accepted and are not yet revoked.
- WordTraceId: 106294
- atomic: true
- Legal Obligation: mandatory
- implement: true
- implementerEnhanced: The
  driver
  [EXTERNAL]
  shall be informed
  when
  [CONDITION]
  emergency stop(s) have been accepted and are
  not yet
  [TIME]
  revoked.
- kind: ordinary

#### 3.10.3 (Requirement Type)
Revocation of an Emergency Message
- WordTraceId: 106390
- atomic: false
- Legal Obligation: not applicable
- implement: false
- kind: Heading

##### 3.10.3.1 (Requirement Type)
The revocation message shall refer to the identity of the concerned emergency message.
- WordTraceId: 106425
- atomic: true
- Legal Obligation: mandatory
- implement: true
- kind: ordinary

##### 3.10.3.2 (Requirement Type)
The revocation messages shall be acknowledged by the on-board equipment, according to the general acknowledgement procedure (see section 3.16.3.5)
- WordTraceId: 106512
- atomic: true
- Legal Obligation: mandatory
- implement: true
- implementerEnhanced: The revocation messages shall be acknowledged by the
  on-board equipment
  [SELF]
  , according to the general acknowledgement procedure (see section 3.16.3.5)
- kind: ordinary
- CrossRefLink -> 3.16.3.5

##### 3.10.3.3 (Requirement Type)
The revocation of an emergency message shall have no effect on the management of other emergency messages possibly received.
- WordTraceId: 106688
- atomic: true
- Legal Obligation: mandatory
- implement: true
- implementerEnhanced: The revocation of an emergency message shall have no effect on the management of other emergency messages
  possibly
  [WEAK]
  received.
- kind: ordinary

##### 3.10.3.4 (Requirement Type)
Intentionally deleted.
- WordTraceId: 106813
- atomic: false
- Legal Obligation: not applicable
- implement: false
- kind: Placeholder

### 3.11 (Requirement Type)
Static Speed Restrictions and Gradients
- WordTraceId: 106837
- atomic: false
- Legal Obligation: not applicable
- implement: false
- kind: Heading

#### 3.11.1 (Requirement Type)
Introduction
- WordTraceId: 106877
- atomic: false
- Legal Obligation: not applicable
- implement: false
- kind: Heading

##### 3.11.1.1 (Requirement Type)
The permitted speed at which the train is allowed to travel shall be limited to different kinds of Static Speed Restrictions and considering the End of Authority/Limit Of Authority.
- WordTraceId: 106891
- atomic: true
- Legal Obligation: mandatory
- implement: true
- kind: ordinary

##### 3.11.1.2 (Requirement Type)
A Static Speed Restriction shall be handled in the same way independent of ETCS level.
- WordTraceId: 107074
- atomic: true
- Legal Obligation: mandatory
- implement: true
- kind: ordinary

#### 3.11.2 (Requirement Type)
Definition of Static Speed Restriction
- WordTraceId: 107161
- atomic: false
- Legal Obligation: not applicable
- implement: false
- kind: Heading

##### 3.11.2.1 (Requirement Type)
Static Speed Restrictions are imposed by the trackside infrastructure, the train characteristics, the signalling and the mode of the on-board equipment.
- WordTraceId: 107200
- atomic: true
- Legal Obligation: unknown
- implement: true
- implementerEnhanced: Static Speed Restrictions are imposed by the
  trackside
  [EXTERNAL]
  infrastructure, the train characteristics, the signalling and the mode of the
  on-board equipment
  [SELF]
  .
- kind: ordinary

##### 3.11.2.2 (Requirement Type)
There are eleven categories of Static Speed Restrictions:
- WordTraceId: 107353
- atomic: true
- Legal Obligation: unknown
- implement: false
- kind: Heading

###### 3.11.2.2.a (Requirement Type)
Static Speed Profile (SSP)
- WordTraceId: 107413
- atomic: true
- Legal Obligation: unknown
- implement: true
- ListNumberText: a)
- kind: ordinary

###### 3.11.2.2.b (Requirement Type)
Axle load Speed Profile (ASP)
- WordTraceId: 107440
- atomic: true
- Legal Obligation: unknown
- implement: true
- ListNumberText: b)
- kind: ordinary

###### 3.11.2.2.c (Requirement Type)
Temporary Speed Restrictions (TSR)
- WordTraceId: 107470
- atomic: true
- Legal Obligation: unknown
- implement: true
- ListNumberText: c)
- kind: ordinary

###### 3.11.2.2.d (Requirement Type)
Maximum Train Speed
- WordTraceId: 107505
- atomic: true
- Legal Obligation: unknown
- implement: true
- ListNumberText: d)
- kind: ordinary

###### 3.11.2.2.e (Requirement Type)
Signalling related speed restriction (only level 1)
- WordTraceId: 107525
- atomic: true
- Legal Obligation: unknown
- implement: true
- ListNumberText: e)
- kind: ordinary

###### 3.11.2.2.f (Requirement Type)
Mode related Speed Restriction.
- WordTraceId: 107577
- atomic: true
- Legal Obligation: unknown
- implement: true
- ListNumberText: f)
- kind: ordinary

###### 3.11.2.2.g (Requirement Type)
STM Max speed (for details refer to Subset-035)
- WordTraceId: 107609
- atomic: true
- Legal Obligation: unknown
- implement: true
- ListNumberText: g)
- kind: ordinary

###### 3.11.2.2.h (Requirement Type)
STM System speed (for details refer to Subset-035)
- WordTraceId: 107657
- atomic: true
- Legal Obligation: unknown
- implement: true
- ListNumberText: h)
- kind: ordinary

###### 3.11.2.2.i (Requirement Type)
Level Crossing speed restriction (LX SR)
- WordTraceId: 107708
- atomic: true
- Legal Obligation: unknown
- implement: true
- ListNumberText: i)
- kind: ordinary

###### 3.11.2.2.j (Requirement Type)
Override function related Speed Restriction
- WordTraceId: 107749
- atomic: true
- Legal Obligation: unknown
- implement: true
- ListNumberText: j)
- kind: ordinary

###### 3.11.2.2.k (Requirement Type)
Speed restriction to ensure a given permitted braking distance (PBD SR) (see 3.11.11)
- WordTraceId: 107793
- atomic: true
- Legal Obligation: unknown
- implement: true
- ListNumberText: k)
- kind: ordinary
- CrossRefLink -> 3.11.11

##### 3.11.2.3 (Requirement Type)
The Static Speed Restriction categories shall be independent of each other. This means that one speed restriction category shall not affect, nor be affected by, any other category of Static Speed Restrictions.
- WordTraceId: 107879
- atomic: false
- Legal Obligation: mandatory
- implement: true
- kind: ordinary

##### 3.11.2.3[2] (Requirement Type)
- WordTraceId: 108090
- atomic: false
- Legal Obligation: not applicable
- implement: false
- kind: Placeholder

###### 3.11.2.3[2].[f]26 (Requirement Type)
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- WordTraceId: 108116
- atomic: false
- Legal Obligation: not applicable
- implement: false
- kind: Figure

###### 3.11.2.3[2].[f]26.C (Requirement Type)
Figure {Figure 26}: Example of Static Speed Restriction categories on a piece of track.
- WordTraceId: 108116
- atomic: true
- Legal Obligation: unknown
- PlainText: Figure 26: Example of Static Speed Restriction categories on a piece of track.
- implement: false
- kind: Figure

##### 3.11.2.4 (Requirement Type)
Depending on the type of Static Speed Restriction train length may have to be used to ensure that the full length of the train has passed a Static Speed Restriction discontinuity before a speed increase shall be taken into account.
- WordTraceId: 108221
- atomic: false
- Legal Obligation: optional
- implement: true
- kind: ordinary

##### 3.11.2.5 (Requirement Type)
Intentionally deleted.
- WordTraceId: 108454
- atomic: false
- Legal Obligation: not applicable
- implement: false
- kind: Placeholder

##### 3.11.2.6 (Requirement Type)
Intentionally deleted.
- WordTraceId: 108478
- atomic: false
- Legal Obligation: not applicable
- implement: false
- kind: Placeholder

#### 3.11.3 (Requirement Type)
Static Speed Profile (SSP)
- WordTraceId: 108501
- atomic: false
- Legal Obligation: not applicable
- implement: false
- kind: Heading

##### 3.11.3.1 (Requirement Type)
PLACEHOLDER REQUIREMENT - DO NOT TRACE
- WordTraceId: 108528
- atomic: false
- Legal Obligation: not applicable
- implement: false
- kind: Placeholder

###### 3.11.3.1.1 (Requirement Type)
The Static Speed Profile (SSP) is a description of the fixed speed restrictions of a given piece of track. The speed restrictions can be related to e.g. maximum line speed, curves, points, tunnel profiles, bridges.
- WordTraceId: 108528
- atomic: false
- Legal Obligation: unknown
- implement: true
- implementerEnhanced: The Static Speed Profile (SSP) is a description of the fixed speed restrictions of a given piece of track. The speed restrictions can be related to
  e.g.
  [WEAK]
  maximum line speed, curves, points, tunnel profiles, bridges.
- kind: ordinary

###### 3.11.3.1.2 (Requirement Type)
The Static Speed Profile is based on factors, which are both track and train dependent. The relationship between track and train characteristics determine the individual Static Speed Profile for each train.
- WordTraceId: 108743
- atomic: false
- Legal Obligation: unknown
- implement: true
- implementerEnhanced: The Static Speed Profile is based on factors, which are both track and train dependent. The relationship between track and train characteristics determine the individual Static Speed Profile
  for each
  [LOOP]
  train.
- kind: ordinary

###### 3.11.3.1.3 (Requirement Type)
It shall be possible for every element (distance between two discontinuities) of a static speed profile to define, if a transition to a higher speed limit than the speed limit specified for this element is permitted before the complete train has left the element.
- WordTraceId: 108951
- atomic: true
- Legal Obligation: mandatory
- implement: true
- implementerEnhanced: It shall be possible
  for every
  [LOOP]
  element (distance between two discontinuities) of a static speed profile to define,
  if
  [CONDITION]
  a transition to a higher speed limit than the speed limit specified for this element is permitted before the complete train has left the element.
- kind: ordinary

##### 3.11.3.2 (Requirement Type)
Static Speed Profile Categories
- WordTraceId: 109215
- atomic: false
- Legal Obligation: not applicable
- implement: false
- kind: Heading

###### 3.11.3.2.1 (Requirement Type)
It shall be possible to transmit several Static Speed Profile Categories; one Basic SSP category and specific SSP categories related to the international train categories.
- WordTraceId: 109247
- atomic: false
- Legal Obligation: mandatory
- implement: true
- kind: ordinary

###### 3.11.3.2.1.1 (Requirement Type)
The specific SSP categories are decomposed into two types:
- WordTraceId: 109419
- atomic: true
- Legal Obligation: unknown
- implement: false
- kind: Heading

###### 3.11.3.2.1.1.a (Requirement Type)
The “Cant Deficiency” SSP categories: the cant deficiency value assigned to one category shall define the maximum speed, determined by suspension design, at which a particular train can traverse a curve and thus can be used to set a specific speed limit in a curve with regards to this category.
- WordTraceId: 109478
- atomic: true
- Legal Obligation: mandatory
- implement: true
- ListNumberText: a)
- kind: ordinary

###### 3.11.3.2.1.1.b (Requirement Type)
The “other specific” SSP categories: it groups all other specific SSP categories corresponding to the other international train categories
- WordTraceId: 109774
- atomic: true
- Legal Obligation: unknown
- implement: true
- ListNumberText: b)
- kind: ordinary

###### 3.11.3.2.1.2 (Requirement Type)
Whenever the type of specific SSP category is not explicitly specified in the following requirements, it shall be interpreted as being applicable for both types of specific SSP categories.
- WordTraceId: 109913
- atomic: true
- Legal Obligation: mandatory
- implement: false
- kind: Definition

###### 3.11.3.2.2 (Requirement Type)
For each part of the Static Speed Profile, the ERTMS/ETCS trackside shall:
- WordTraceId: 110102
- atomic: true
- Legal Obligation: not applicable
- implement: false
- implementerEnhanced: For each
  [LOOP]
  part of the Static Speed Profile, the ERTMS/ETCS
  trackside
  [EXTERNAL]
  shall:
- kind: Heading

###### 3.11.3.2.2.a (Requirement Type)
always give the Basic SSP, which shall be considered as the default “Cant Deficiency” SSP
- WordTraceId: 110177
- atomic: true
- Legal Obligation: mandatory
- implement: true
- implementerEnhanced: always give the Basic SSP, which shall be considered as the default “
  Cant Deficiency
  [LINKED_PHRASE]
  ” SSP
- ListNumberText: a)
- kind: ordinary
- KnownTermLink -> 3.11.3.2.1.1.a

###### 3.11.3.2.2.b (Requirement Type)
optionally give one or more specific SSPs
- WordTraceId: 110267
- atomic: true
- Legal Obligation: mandatory
- implement: true
- ListNumberText: b)
- kind: ordinary

###### 3.11.3.2.2.c (Requirement Type)
specify, for each “other specific” SSP, whether it replaces or not the “Cant Deficiency” SSP as selected by the ERTMS/ETCS on-board equipment according to 3.11.3.2.3
- WordTraceId: 110309
- atomic: true
- Legal Obligation: mandatory
- implement: true
- implementerEnhanced: specify,
  for each
  [LOOP]
  “
  other specific
  [LINKED_PHRASE]
  ” SSP,
  whether
  [CONDITION]
  it replaces or not the “
  Cant Deficiency
  [LINKED_PHRASE]
  ” SSP as selected by the
  ERTMS/ETCS on-board equipment
  [SELF]
  according to 3.11.3.2.3
- ListNumberText: c)
- kind: ordinary
- CrossRefLink -> 3.11.3.2.3
- KnownTermLink -> 3.11.3.2.1.1.a
- KnownTermLink -> 3.11.3.2.1.1.b

###### 3.11.3.2.3 (Requirement Type)
For each part of the Static Speed Profile, the ERTMS/ETCS on-board equipment shall select the SSP best suiting its “Cant Deficiency” train category, according to the following order of preference:
- WordTraceId: 110475
- atomic: true
- Legal Obligation: not applicable
- implement: false
- implementerEnhanced: For each
  [LOOP]
  part of the Static Speed Profile, the
  ERTMS/ETCS on-board equipment
  [SELF]
  shall select the SSP
  best
  [WEAK]
  suiting its “
  Cant Deficiency
  [LINKED_PHRASE]
  ” train category, according to the following order of preference:
- kind: Heading
- KnownTermLink -> 3.11.3.2.1.1.a

###### 3.11.3.2.3.a (Requirement Type)
if available, the “Cant Deficiency” SSP matching its “Cant Deficiency” train category, OR
- WordTraceId: 110672
- atomic: true
- Legal Obligation: mandatory
- implement: true
- implementerEnhanced: if
  [CONDITION]
  available, the “
  Cant Deficiency
  [LINKED_PHRASE]
  ” SSP matching its “
  Cant Deficiency
  [LINKED_PHRASE]
  ” train category, OR
- ListNumberText: a)
- kind: ordinary
- KnownTermLink -> 3.11.3.2.1.1.a

###### 3.11.3.2.3.b (Requirement Type)
if available, the “Cant Deficiency” SSP with the highest Cant Deficiency value below the value of its “Cant Deficiency” train category, OR
- WordTraceId: 110762
- atomic: true
- Legal Obligation: mandatory
- implement: true
- implementerEnhanced: if
  [CONDITION]
  available, the “
  Cant Deficiency
  [LINKED_PHRASE]
  ” SSP with the highest
  Cant Deficiency
  [LINKED_PHRASE]
  value
  below
  [WEAK]
  the value of its “
  Cant Deficiency
  [LINKED_PHRASE]
  ” train category, OR
- ListNumberText: b)
- kind: ordinary
- KnownTermLink -> 3.11.3.2.1.1.a

###### 3.11.3.2.3.c (Requirement Type)
the Basic SSP
- WordTraceId: 110901
- atomic: true
- Legal Obligation: mandatory
- implement: true
- ListNumberText: c)
- kind: ordinary

###### 3.11.3.2.3.1 (Requirement Type)
Intentionally deleted.
- WordTraceId: 110915
- atomic: false
- Legal Obligation: not applicable
- implement: false
- kind: Placeholder

###### 3.11.3.2.4 (Requirement Type)
Intentionally deleted.
- WordTraceId: 110938
- atomic: false
- Legal Obligation: not applicable
- implement: false
- kind: Placeholder

###### 3.11.3.2.5 (Requirement Type)
“Other Specific” SSP categories not relevant to the current train shall be ignored.
- WordTraceId: 110961
- atomic: true
- Legal Obligation: mandatory
- implement: true
- implementerEnhanced: “
  Other Specific
  [LINKED_PHRASE]
  ” SSP categories not relevant to the current train shall be ignored.
- kind: ordinary
- KnownTermLink -> 3.11.3.2.1.1.b

###### 3.11.3.2.6 (Requirement Type)
For each part of the Static Speed Profile, the ERTMS/ETCS on-board equipment in a train belonging to at least one or more “other international” train categories shall use the most restrictive speed amongst:
- WordTraceId: 111045
- atomic: true
- Legal Obligation: mandatory
- implement: true
- implementerEnhanced: For each
  [LOOP]
  part of the Static Speed Profile, the
  ERTMS/ETCS on-board equipment
  [SELF]
  in a train belonging to
  at least
  [WEAK]
  one or more “other international” train categories shall use the most restrictive speed amongst:
- kind: ordinary

###### 3.11.3.2.6.a (Requirement Type)
the ” Cant Deficiency” SSP as selected in 3.11.3.2.3, only if none of the “other specific” SSP categories matching the train categories replaces the ” Cant Deficiency” SSP, AND
- WordTraceId: 111252
- atomic: true
- Legal Obligation: mandatory
- implement: true
- implementerEnhanced: the ”
  Cant Deficiency
  [LINKED_PHRASE]
  ” SSP as selected in 3.11.3.2.3, only
  if
  [CONDITION]
  none of the “
  other specific
  [LINKED_PHRASE]
  ” SSP categories matching the train categories replaces the ”
  Cant Deficiency
  [LINKED_PHRASE]
  ” SSP, AND
- ListNumberText: a)
- kind: ordinary
- CrossRefLink -> 3.11.3.2.3
- KnownTermLink -> 3.11.3.2.1.1.a
- KnownTermLink -> 3.11.3.2.1.1.b

###### 3.11.3.2.6.b (Requirement Type)
all the “other specific” SSP categories matching the “other international” train categories.
- WordTraceId: 111429
- atomic: true
- Legal Obligation: mandatory
- implement: true
- implementerEnhanced: all the “
  other specific
  [LINKED_PHRASE]
  ” SSP categories matching the “
  other international
  [LINKED_PHRASE]
  ” train categories.
- ListNumberText: b)
- kind: ordinary
- KnownTermLink -> 3.11.3.2.6
- KnownTermLink -> 3.11.3.2.1.1.b

##### 3.11.3.3 (Requirement Type)
Train categories
- WordTraceId: 111522
- atomic: false
- Legal Obligation: not applicable
- implement: false
- kind: Heading

###### 3.11.3.3.1 (Requirement Type)
A maximum of 31 train categories shall be defined to match the SSP categories. 16 “Cant Deficiency” train categories and 15 “other international” train categories.
- WordTraceId: 111539
- atomic: true
- Legal Obligation: mandatory
- implement: true
- implementerEnhanced: A maximum of 31 train categories shall be defined to match the SSP categories. 16 “
  Cant Deficiency
  [LINKED_PHRASE]
  ” train categories and 15 “
  other international
  [LINKED_PHRASE]
  ” train categories.
- kind: ordinary
- KnownTermLink -> 3.11.3.2.6
- KnownTermLink -> 3.11.3.2.1.1.a

###### 3.11.3.3.2 (Requirement Type)
A train shall always belong to one and only one “Cant Deficiency” train category and may optionally belong to one or more “other international” train categories.
- WordTraceId: 111703
- atomic: false
- Legal Obligation: mixed
- implement: true
- implementerEnhanced: A train shall always belong to one and only one “
  Cant Deficiency
  [LINKED_PHRASE]
  ” train category and may optionally belong to one or more “
  other international
  [LINKED_PHRASE]
  ” train categories.
- kind: ordinary
- KnownTermLink -> 3.11.3.2.6
- KnownTermLink -> 3.11.3.2.1.1.a

###### 3.11.3.3.3 (Requirement Type)
The train category(ies) to which a train belongs shall be a part of its Train Data.
- WordTraceId: 111865
- atomic: true
- Legal Obligation: mandatory
- implement: true
- kind: ordinary

#### 3.11.4 (Requirement Type)
Axle load Speed Profile
- WordTraceId: 111949
- atomic: false
- Legal Obligation: not applicable
- implement: false
- kind: Heading

##### 3.11.4.1 (Requirement Type)
It shall be possible to define an Axle load Speed Profile as a non-continuous profile.
- WordTraceId: 111973
- atomic: true
- Legal Obligation: mandatory
- implement: true
- kind: ordinary

##### 3.11.4.2 (Requirement Type)
For each section with a speed restriction due to axle load, the different speed value(s) and for which minimum axle load category this speed value(s) applies shall be specified.
- WordTraceId: 112060
- atomic: true
- Legal Obligation: mandatory
- implement: true
- implementerEnhanced: For each
  [LOOP]
  section with a speed restriction due to axle load, the different speed value(s) and for which minimum axle load category this speed value(s) applies shall be specified.
- kind: ordinary

###### 3.11.4.2.1 (Requirement Type)
Note: Different speed restrictions depending on the axle load category can be applicable to the same distance.
- WordTraceId: 112238
- atomic: false
- Legal Obligation: not applicable
- implement: false
- kind: Note

##### 3.11.4.3 (Requirement Type)
The ERTMS/ETCS on-board equipment shall consider the most restrictive speed restriction that is associated with any axle load category lower than, or equal to that of the train.
- WordTraceId: 112349
- atomic: true
- Legal Obligation: mandatory
- implement: true
- implementerEnhanced: The
  ERTMS/ETCS on-board equipment
  [SELF]
  shall consider the most restrictive speed restriction that is associated with any axle load category lower than, or equal to that of the train.
- kind: ordinary

##### 3.11.4.4 (Requirement Type)
For trains with an axle load category lower than the minimum axle load category given in the profile, the ERTMS/ETCS on-board equipment shall not consider any speed restriction due to axle load.
- WordTraceId: 112527
- atomic: true
- Legal Obligation: mandatory
- implement: true
- implementerEnhanced: For trains with an axle load category lower than the minimum axle load category given in the profile, the
  ERTMS/ETCS on-board equipment
  [SELF]
  shall not consider any speed restriction due to axle load.
- kind: ordinary

##### 3.11.4.5 (Requirement Type)
The initial state for Axle load Speed Profile shall be “no restriction due to axle load”.
- WordTraceId: 112722
- atomic: true
- Legal Obligation: mandatory
- implement: true
- kind: ordinary

##### 3.11.4.6 (Requirement Type)
Whether a speed increase after the axle load speed restriction shall be delayed with train length, shall be determined by the axle load speed profile information sent to the on-board equipment.
- WordTraceId: 112812
- atomic: false
- Legal Obligation: mandatory
- implement: true
- implementerEnhanced: Whether
  [CONDITION]
  a speed increase
  after
  [TIME]
  the axle load speed restriction shall be delayed with train length, shall be determined by the axle load speed profile information sent to the
  on-board equipment
  [SELF]
  .
- kind: ordinary

#### 3.11.5 (Requirement Type)
Temporary Speed Restrictions
- WordTraceId: 113006
- atomic: false
- Legal Obligation: not applicable
- implement: false
- kind: Heading

##### 3.11.5.1 (Requirement Type)
The temporary speed restriction is defined in order to enable a separate category of track infrastructure speed restriction, which can be used for working areas etc.
- WordTraceId: 113035
- atomic: true
- Legal Obligation: unknown
- implement: true
- implementerEnhanced: The temporary speed restriction is defined in order to enable a separate category of track infrastructure speed restriction, which can be used for working areas
  etc.
  [WEAK]
- kind: ordinary

##### 3.11.5.2 (Requirement Type)
All Temporary Speed Restrictions shall be independent of each other. This means that an individual Temporary Speed Restriction shall not affect, nor be affected by, any other individual Temporary Speed Restriction.
- WordTraceId: 113201
- atomic: false
- Legal Obligation: mandatory
- implement: true
- kind: ordinary

##### 3.11.5.3 (Requirement Type)
Whether a speed increase after the temporary speed restriction shall be delayed with train length, shall be determined by the temporary speed restriction information sent to the on-board equipment.
- WordTraceId: 113417
- atomic: false
- Legal Obligation: mandatory
- implement: true
- implementerEnhanced: Whether
  [CONDITION]
  a speed increase
  after
  [TIME]
  the temporary speed restriction shall be delayed with train length, shall be determined by the temporary speed restriction information sent to the
  on-board equipment
  [SELF]
  .
- kind: ordinary

##### 3.11.5.4 (Requirement Type)
When two or more temporary speed restrictions overlap, the most restrictive speed of the overlapping temporary speed restrictions shall be used in the area of overlap.
- WordTraceId: 113615
- atomic: true
- Legal Obligation: mandatory
- implement: true
- implementerEnhanced: When
  [CONDITION]
  two or more temporary speed restrictions overlap, the most restrictive speed of the overlapping temporary speed restrictions shall be used in the area of overlap.
- kind: ordinary

##### 3.11.5.5 (Requirement Type)
Each Temporary Speed Restriction shall have an identity to make it possible to revoke the Temporary Speed Restriction using its identity. The speed restriction shall be revoked immediately when revocation is received from trackside, without delay for the train length.
- WordTraceId: 113783
- atomic: false
- Legal Obligation: mandatory
- implement: true
- implementerEnhanced: Each Temporary Speed Restriction shall have an identity to make it possible to revoke the Temporary Speed Restriction using its identity. The speed restriction shall be revoked
  immediately
  [WEAK]
  when
  [CONDITION]
  revocation is received from
  trackside
  [EXTERNAL]
  , without
  delay
  [TIME]
  for the train length.
- kind: ordinary

##### 3.11.5.6 (Requirement Type)
It shall be possible to identify whether a Temporary Speed Restriction is possible to revoke or not.
- WordTraceId: 114052
- atomic: true
- Legal Obligation: mandatory
- implement: true
- implementerEnhanced: It shall be possible to identify
  whether
  [CONDITION]
  a Temporary Speed Restriction is possible to revoke or not.
- kind: ordinary

##### 3.11.5.7 (Requirement Type)
A new Temporary Speed Restriction shall not replace a previously received Temporary Speed Restriction with another identity.
- WordTraceId: 114153
- atomic: true
- Legal Obligation: mandatory
- implement: true
- kind: ordinary

##### 3.11.5.8 (Requirement Type)
Temporary Speed Restrictions shall only be revoked on request from the trackside.
- WordTraceId: 114279
- atomic: true
- Legal Obligation: mandatory
- implement: true
- implementerEnhanced: Temporary Speed Restrictions shall only be revoked on request from the
  trackside
  [EXTERNAL]
  .
- kind: ordinary

##### 3.11.5.9 (Requirement Type)
If the on-board equipment receives a new Temporary Speed Restriction (TSR) with the same identity as an already received TSR, the new Temporary Speed Restriction shall replace the previous one, except when the Temporary Speed Restriction is identified as non revocable in which case this shall be considered as an additional TSR.
- WordTraceId: 114362
- atomic: false
- Legal Obligation: mandatory
- implement: true
- implementerEnhanced: If
  [CONDITION]
  the
  on-board equipment
  [SELF]
  receives a new Temporary Speed Restriction (TSR) with the same identity as an already received TSR, the new Temporary Speed Restriction shall replace the previous one, except
  when
  [CONDITION]
  the Temporary Speed Restriction is identified as non revocable in which case this shall be considered as an additional TSR.
- kind: ordinary

##### 3.11.5.10 (Requirement Type)
In case the train has changed its orientation any Temporary Speed Restriction shall be deleted (operational requirement: will be executed due to the mode change).
- WordTraceId: 114692
- atomic: true
- Legal Obligation: mandatory
- implement: true
- implementerEnhanced: In case
  [CONDITION]
  the train has changed its orientation any Temporary Speed Restriction shall be deleted (operational requirement: will be executed due to the mode change).
- kind: ordinary

##### 3.11.5.11 (Requirement Type)
Intentionally deleted.
- WordTraceId: 114855
- atomic: false
- Legal Obligation: not applicable
- implement: false
- kind: Placeholder

##### 3.11.5.12 (Requirement Type)
It shall be possible for the RBC to order an ERTMS/ETCS on-board equipment in Level 2 or 3 to reject revocable TSRs from balises.
- WordTraceId: 114878
- atomic: true
- Legal Obligation: mandatory
- implement: true
- implementerEnhanced: It shall be possible for the
  RBC
  [EXTERNAL]
  to order an
  ERTMS/ETCS on-board equipment
  [SELF]
  in Level 2 or 3 to reject revocable TSRs from
  balises
  [EXTERNAL]
  .
- kind: ordinary

##### 3.11.5.13 (Requirement Type)
When ERTMS/ETCS on-board equipment has accepted an order to reject revocable TSRs from balises, this inhibition shall be stored and shall be effective immediately, but only for revocable TSRs received from balises thereafter.
- WordTraceId: 115008
- atomic: false
- Legal Obligation: mandatory
- implement: true
- implementerEnhanced: When
  [CONDITION]
  ERTMS/ETCS on-board equipment
  [SELF]
  has accepted an order to reject revocable TSRs from
  balises
  [EXTERNAL]
  , this inhibition shall be stored and shall be effective
  immediately
  [WEAK]
  , but only for revocable TSRs received from
  balises
  [EXTERNAL]
  thereafter.
- kind: ordinary

##### 3.11.5.14 (Requirement Type)
The inhibition of revocable TSRs from balises shall be deleted if any of the following occurs:
- WordTraceId: 115235
- atomic: true
- Legal Obligation: not applicable
- implement: false
- implementerEnhanced: The inhibition of revocable TSRs from
  balises
  [EXTERNAL]
  shall be deleted
  if
  [CONDITION]
  any of the following occurs:
- kind: Heading

###### 3.11.5.14.*[1] (Requirement Type)
the communication session established with the RBC that ordered the inhibition is terminated, OR
- WordTraceId: 115330
- atomic: true
- Legal Obligation: mandatory
- implement: true
- implementerEnhanced: the communication session established with the
  RBC
  [EXTERNAL]
  that ordered the inhibition is terminated, OR
- ListNumberText: ·
- kind: ordinary

###### 3.11.5.14.*[2] (Requirement Type)
in case of RBC/RBC handover, the train front end crosses the RBC/RBC border.
- WordTraceId: 115427
- atomic: true
- Legal Obligation: mandatory
- implement: true
- implementerEnhanced: in case of
  [CONDITION]
  RBC
  [EXTERNAL]
  /
  RBC
  [EXTERNAL]
  handover, the train front end crosses the
  RBC
  [EXTERNAL]
  /
  RBC
  [EXTERNAL]
  border.
- ListNumberText: ·
- kind: ordinary

##### 3.11.5.15 (Requirement Type)
Note: this inhibition may be useful in Level 1 / Level 2 mixed signalling applications when the RBC has more precise information about restrictions than can be given from balises. The RBC may then order inhibition of revocable TSRs from balises and instead send more precise TSRs to the train.
- WordTraceId: 115504
- atomic: false
- Legal Obligation: optional
- implement: false
- implementerEnhanced: Note: this inhibition may be
  useful
  [WEAK]
  in Level 1 / Level 2 mixed signalling applications
  when
  [CONDITION]
  the
  RBC
  [EXTERNAL]
  has more precise information about restrictions than can be given from
  balises
  [EXTERNAL]
  . The
  RBC
  [EXTERNAL]
  may then order inhibition of revocable TSRs from
  balises
  [EXTERNAL]
  and instead send more precise TSRs to the train.
- kind: Note

#### 3.11.6 (Requirement Type)
Signalling related speed restrictions
- WordTraceId: 115798
- atomic: false
- Legal Obligation: not applicable
- implement: false
- kind: Heading

##### 3.11.6.1 (Requirement Type)
In level 1, it shall be possible to send to the on-board equipment a speed restriction with a value depending on the current state of signalling.
- WordTraceId: 115836
- atomic: true
- Legal Obligation: mandatory
- implement: true
- implementerEnhanced: In level 1, it shall be possible to send to the
  on-board equipment
  [SELF]
  a speed restriction with a value depending on the current state of signalling.
- kind: ordinary

##### 3.11.6.2 (Requirement Type)
This speed value shall be taken into account by the on-board equipment as soon as it is received on-board, with the exception of a signalling related speed restriction from an infill device. In case of infill information the speed restriction shall be taken into account from the location reference of the balise group at the next main signal.
- WordTraceId: 115982
- atomic: false
- Legal Obligation: mandatory
- implement: true
- implementerEnhanced: This speed value shall be taken into account by the
  on-board equipment
  [SELF]
  as soon as
  [WEAK]
  it is received on-board, with the exception of a signalling related speed restriction from an infill device.
  In case of
  [CONDITION]
  infill information the speed restriction shall be taken into account from the location reference of the
  balise group
  [EXTERNAL]
  at the next main signal.
- kind: ordinary

##### 3.11.6.3 (Requirement Type)
The speed restriction shall be valid until a new signalling related speed restriction is received.
- WordTraceId: 116326
- atomic: true
- Legal Obligation: mandatory
- implement: true
- implementerEnhanced: The speed restriction shall be valid
  until
  [TIME]
  a new signalling related speed restriction is received.
- kind: ordinary

###### 3.11.6.3.1 (Requirement Type)
If the ERTMS/ETCS on-board equipment switches from level 1 to level 2/3, the signalling related speed restriction shall remain valid until a L2/3 MA is accepted by the ERTMS/ETCS on-board equipment
- WordTraceId: 116425
- atomic: true
- Legal Obligation: mandatory
- implement: true
- implementerEnhanced: If
  [CONDITION]
  the
  ERTMS/ETCS on-board equipment
  [SELF]
  switches from level 1 to level 2/3, the signalling related speed restriction shall remain valid
  until
  [TIME]
  a L2/3 MA is accepted by the
  ERTMS/ETCS on-board equipment
  [SELF]
- kind: ordinary

##### 3.11.6.4 (Requirement Type)
In case of a signal at danger the signalling related speed restriction shall have value zero, which shall be evaluated by the ERTMS/ETCS on-board equipment not as a speed limit but as a train trip order.
- WordTraceId: 116623
- atomic: false
- Legal Obligation: mandatory
- implement: true
- implementerEnhanced: In case of
  [CONDITION]
  a signal at danger the signalling related speed restriction shall have value zero, which shall be evaluated by the
  ERTMS/ETCS on-board equipment
  [SELF]
  not as a speed limit but as a train trip order.
- kind: ordinary

##### 3.11.6.5 (Requirement Type)
In case of infill information the signalling related speed restriction at zero shall be ignored.
- WordTraceId: 116827
- atomic: true
- Legal Obligation: mandatory
- implement: true
- implementerEnhanced: In case of
  [CONDITION]
  infill information the signalling related speed restriction at zero shall be ignored.
- kind: ordinary

###### 3.11.6.5.1 (Requirement Type)
Note: The infill information will also include an EOA at the next main signal that will be supervised according to the normal rules.
- WordTraceId: 116924
- atomic: false
- Legal Obligation: not applicable
- implement: false
- kind: Note

#### 3.11.7 (Requirement Type)
Mode related speed restrictions
- WordTraceId: 117057
- atomic: false
- Legal Obligation: not applicable
- implement: false
- kind: Heading

##### 3.11.7.1 (Requirement Type)
The value of the mode related speed restriction shall be determined by the corresponding national value or the corresponding default values if the national values are not applicable.
- WordTraceId: 117089
- atomic: true
- Legal Obligation: mandatory
- implement: true
- implementerEnhanced: The value of the mode related speed restriction shall be determined by the corresponding national value or the corresponding default values
  if
  [CONDITION]
  the national values are not applicable.
- kind: ordinary

###### 3.11.7.1.1 (Requirement Type)
Exception 1: For the modes On-sight, Limited Supervision and Shunting the speed limit can also be given from the trackside. The speed limit given from the trackside shall prevail over the National value and the default value.
- WordTraceId: 117272
- atomic: false
- Legal Obligation: mandatory
- implement: true
- implementerEnhanced: Exception 1: For the modes On-sight, Limited Supervision and Shunting the speed limit can also be given from the
  trackside
  [EXTERNAL]
  . The speed limit given from the
  trackside
  [EXTERNAL]
  shall prevail over the National value and the default value.
- kind: ordinary

###### 3.11.7.1.2 (Requirement Type)
Exception 2: For the mode Reversing there is no National/Default value. The speed limit is always given from trackside.
- WordTraceId: 117499
- atomic: false
- Legal Obligation: unknown
- implement: true
- implementerEnhanced: Exception 2: For the mode Reversing there is no National/Default value. The speed limit is always given from
  trackside
  [EXTERNAL]
  .
- kind: ordinary

###### 3.11.7.1.3 (Requirement Type)
Exception 3: For the mode Staff Responsible the speed limit can also be entered by the driver. The speed limit given by the driver shall prevail over the National/Default value.
- WordTraceId: 117620
- atomic: false
- Legal Obligation: mandatory
- implement: true
- implementerEnhanced: Exception 3: For the mode Staff Responsible the speed limit can also be entered by the
  driver
  [EXTERNAL]
  . The speed limit given by the
  driver
  [EXTERNAL]
  shall prevail over the National/Default value.
- kind: ordinary

#### 3.11.8 (Requirement Type)
Train related speed restriction
- WordTraceId: 117798
- atomic: false
- Legal Obligation: not applicable
- implement: false
- kind: Heading

##### 3.11.8.1 (Requirement Type)
It shall be possible to define the maximum train speed related to the actual performance and configuration of the train.
- WordTraceId: 117830
- atomic: true
- Legal Obligation: mandatory
- implement: true
- kind: ordinary

#### 3.11.9 (Requirement Type)
LX speed restriction
- WordTraceId: 117951
- atomic: false
- Legal Obligation: not applicable
- implement: false
- kind: Heading

##### 3.11.9.1 (Requirement Type)
It shall be possible to define a LX speed restriction when the train has to pass a non protected Level Crossing.
- WordTraceId: 117972
- atomic: true
- Legal Obligation: mandatory
- implement: true
- implementerEnhanced: It shall be possible to define a LX speed restriction
  when
  [CONDITION]
  the train has to pass a non protected Level Crossing.
- kind: ordinary

#### 3.11.10 (Requirement Type)
Override function related Speed Restriction
- WordTraceId: 118085
- atomic: false
- Legal Obligation: not applicable
- implement: false
- kind: Heading

##### 3.11.10.1 (Requirement Type)
While the “override” function is active, the override speed limit (national /default value) shall be taken into account.
- WordTraceId: 118129
- atomic: true
- Legal Obligation: mandatory
- implement: true
- implementerEnhanced: While
  [TIME]
  the “override” function is active, the override speed limit (national /default value) shall be taken into account.
- kind: ordinary

#### 3.11.11 (Requirement Type)
Speed restriction
to ensure permitted braking distance
- WordTraceId: 118250
- atomic: false
- Legal Obligation: not applicable
- implement: false
- kind: Heading

##### 3.11.11.1 (Requirement Type)
It shall be possible for trackside to request on-board to calculate a speed restriction which ensures that the train stops within a given permitted braking distance.
- WordTraceId: 118305
- atomic: true
- Legal Obligation: mandatory
- implement: true
- implementerEnhanced: It shall be possible for
  trackside
  [EXTERNAL]
  to request on-board to calculate a speed restriction which ensures that the train stops within a given permitted braking distance.
- kind: ordinary

##### 3.11.11.2 (Requirement Type)
The order shall be given by means of a non-continuous profile defining:
- WordTraceId: 118471
- atomic: true
- Legal Obligation: mandatory
- implement: true
- kind: ordinary

###### 3.11.11.2.*[1] (Requirement Type)
The start and end location for the speed restriction
- WordTraceId: 118543
- atomic: true
- Legal Obligation: unknown
- implement: true
- ListNumberText: ·
- kind: ordinary

###### 3.11.11.2.*[2] (Requirement Type)
The permitted braking distance used to calculate the speed restriction value
- WordTraceId: 118596
- atomic: true
- Legal Obligation: unknown
- implement: true
- ListNumberText: ·
- kind: ordinary

###### 3.11.11.2.*[3] (Requirement Type)
Whether the permitted braking distance is to be achieved with the Service Brake or Emergency Brake
- WordTraceId: 118673
- atomic: true
- Legal Obligation: unknown
- implement: true
- implementerEnhanced: Whether
  [CONDITION]
  the permitted braking distance is to be achieved with the Service Brake or Emergency Brake
- ListNumberText: ·
- kind: ordinary

###### 3.11.11.2.*[4] (Requirement Type)
A single gradient value applicable for the calculation
- WordTraceId: 118772
- atomic: true
- Legal Obligation: unknown
- implement: true
- ListNumberText: ·
- kind: ordinary

##### 3.11.11.3 (Requirement Type)
The speed restriction shall be calculated when ERTMS/ETCS on-board receives the permitted braking distance information from trackside, and shall be re-calculated only if the brake characteristics of the train taken into account for the calculation of the speed restriction changes.
- WordTraceId: 118827
- atomic: false
- Legal Obligation: mandatory
- implement: true
- implementerEnhanced: The speed restriction shall be calculated
  when
  [CONDITION]
  ERTMS/ETCS on-board
  [SELF]
  receives the permitted braking distance information from
  trackside
  [EXTERNAL]
  , and shall be
  re-calculated
  [AGAIN]
  only
  if
  [CONDITION]
  the brake characteristics of the train taken into account for the calculation of the speed restriction changes.
- kind: ordinary

##### 3.11.11.4 (Requirement Type)
The calculation of the speed restriction by the on-board shall be executed as follows:
- WordTraceId: 119109
- atomic: true
- Legal Obligation: mandatory
- implement: true
- kind: ordinary

###### 3.11.11.4.*[1] (Requirement Type)
The gradient value received from trackside shall be applied for EBD and/or SBD calculation.
- WordTraceId: 119196
- atomic: true
- Legal Obligation: mandatory
- implement: true
- implementerEnhanced: The gradient value received from
  trackside
  [EXTERNAL]
  shall be applied for EBD and/or SBD calculation.
- ListNumberText: ·
- kind: ordinary

###### 3.11.11.4.*[2] (Requirement Type)
For the calculation of the EBI limit: the estimated acceleration shall be set to “zero”, the compensation of the speed measurement inaccuracy, if not inhibited, shall be set to a Fixed Value (see Appendix A3.1).
- WordTraceId: 119288
- atomic: false
- Legal Obligation: mandatory
- implement: true
- implementerEnhanced: For the calculation of the EBI limit: the estimated acceleration shall be set to “zero”, the compensation of the speed measurement inaccuracy,
  if
  [CONDITION]
  not inhibited, shall be set to a Fixed Value (see Appendix A3.1).
- ListNumberText: ·
- kind: ordinary
- CrossRefLink -> A.3.1

###### 3.11.11.4.*[3] (Requirement Type)
If the permitted braking distance is to be achieved with the emergency brake, the EBI limit shall be calculated like the EBI limit for an SvL in a target speed supervision towards an EOA.
- WordTraceId: 119500
- atomic: true
- Legal Obligation: mandatory
- implement: true
- implementerEnhanced: If
  [CONDITION]
  the permitted braking distance is to be achieved with the emergency brake, the EBI limit shall be calculated like the EBI limit for an SvL in a target speed supervision towards an EOA.
- ListNumberText: ·
- kind: ordinary

###### 3.11.11.4.*[4] (Requirement Type)
If the permitted braking distance is to be achieved with the service brake, the FLOI limit shall be calculated like the FLOI limit of the target speed supervision for a combined EOA/SvL location.
- WordTraceId: 119688
- atomic: true
- Legal Obligation: mandatory
- implement: true
- implementerEnhanced: If
  [CONDITION]
  the permitted braking distance is to be achieved with the service brake, the FLOI limit shall be calculated like the FLOI limit of the target speed supervision for a combined EOA/SvL location.
- ListNumberText: ·
- kind: ordinary

##### 3.11.11.4[2] (Requirement Type)
The result of the calculation is an EBI, or FLOI, target speed supervision value at the permitted braking distance in rear of the stop location.
- WordTraceId: 119884
- atomic: true
- Legal Obligation: unknown
- implement: true
- kind: ordinary

##### 3.11.11.5 (Requirement Type)
The derived EBI, or FLOI, target speed supervision value shall be used as the SB ceiling speed intervention limit for the speed restriction.
- WordTraceId: 120029
- atomic: true
- Legal Obligation: mandatory
- implement: true
- kind: ordinary

##### 3.11.11.6 (Requirement Type)
From the SB ceiling speed intervention limit according to the previous clause, the Permitted Speed limit inside the speed restriction shall be calculated by:
- WordTraceId: 120170
- atomic: true
- Legal Obligation: mandatory
- implement: true
- kind: ordinary

###### 3.11.11.6.*[1] (Requirement Type)
Subtracting the applicable speed interval between Permitted Speed limit and SB intervention (see 3.13.9.2.5)
.
The speed interval shall be approximated by using the SB ceiling speed intervention limit instead of the MRSP speed limit in the formula.
- WordTraceId: 120328
- atomic: false
- Legal Obligation: mandatory
- PlainText: Subtracting the applicable speed interval between Permitted Speed limit and SB intervention (see 3.13.9.2.5). The speed interval shall be approximated by using the SB ceiling speed intervention limit instead of the MRSP speed limit in the formula.
- implement: true
- ListNumberText: ·
- kind: ordinary
- CrossRefLink -> 3.13.9.2.5

###### 3.11.11.6.*[2] (Requirement Type)
Rounding the result down to the next lower multiple of 5km/h.
- WordTraceId: 120605
- atomic: true
- Legal Obligation: unknown
- implement: true
- ListNumberText: ·
- kind: ordinary

##### 3.11.11.7 (Requirement Type)
The initial state for Speed Restrictions to Ensure Permitted Braking Distance shall be “no speed restriction”.
- WordTraceId: 120667
- atomic: true
- Legal Obligation: mandatory
- implement: true
- kind: ordinary

#### 3.11.12 (Requirement Type)
Gradients
- WordTraceId: 120778
- atomic: false
- Legal Obligation: not applicable
- implement: false
- kind: Heading

##### 3.11.12.1 (Requirement Type)
The gradient information for a given piece of track shall be transmitted to the on-board equipment in form of a gradient profile.
- WordTraceId: 120788
- atomic: true
- Legal Obligation: mandatory
- implement: true
- implementerEnhanced: The gradient information for a given piece of track shall be transmitted to the
  on-board equipment
  [SELF]
  in form of a gradient profile.
- kind: ordinary

##### 3.11.12.2 (Requirement Type)
The gradient profile shall be continuous, i.e., give a gradient value for each location within the piece of track covered by the profile.
- WordTraceId: 120918
- atomic: true
- Legal Obligation: mandatory
- implement: true
- implementerEnhanced: The gradient profile shall be continuous, i.e., give a gradient value
  for each
  [LOOP]
  location within the piece of track covered by the profile.
- kind: ordinary

##### 3.11.12.3 (Requirement Type)
A gradient value shall be identified as a positive value for an uphill slope, and with a negative value for a downhill slope.
- WordTraceId: 121056
- atomic: true
- Legal Obligation: mandatory
- implement: true
- kind: ordinary

##### 3.11.12.4 (Requirement Type)
The gradient profile shall contain the gradient information as a sequence of gradient values, constant between two defined locations each, see Figure 27.
- WordTraceId: 121182
- atomic: true
- Legal Obligation: mandatory
- implement: true
- kind: ordinary
- CrossRefLink -> 3.11.12.4[2].[f]27.C

##### 3.11.12.4[2] (Requirement Type)
- WordTraceId: 121362
- atomic: false
- Legal Obligation: not applicable
- implement: false
- kind: Placeholder

###### 3.11.12.4[2].[f]27 (Requirement Type)
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- WordTraceId: 121390
- atomic: false
- Legal Obligation: not applicable
- implement: false
- kind: Figure

###### 3.11.12.4[2].[f]27.C (Requirement Type)
Figure {Figure 27}: Gradient profile
- WordTraceId: 121390
- atomic: true
- Legal Obligation: unknown
- PlainText: Figure 27: Gradient profile
- implement: false
- implementerEnhanced: Figure 27: Gradient profile
- kind: Figure

###### 3.11.12.4[2].1 (Requirement Type)
Note:
The figure above symbolises the engineering process to provide the values of gradients. Following the track height, the track must be split in segments giving for each segment a gradient value.
- WordTraceId: 121443
- atomic: false
- Legal Obligation: not applicable
- implement: false
- implementerEnhanced: Note: The figure
  above
  [WEAK]
  symbolises the engineering process to provide the values of gradients. Following the track height, the track must be split in segments giving
  for each
  [LOOP]
  segment a gradient value.
- ListNumberText: 3.11.12.4.1
- kind: Note

##### 3.11.12.5 (Requirement Type)
It shall be possible via balise groups to send to the on-board equipment a default gradient for TSR supervision, to be used for the parts of the track not covered by the gradient profile.
- WordTraceId: 121643
- atomic: true
- Legal Obligation: mandatory
- implement: true
- implementerEnhanced: It shall be possible via
  balise groups
  [EXTERNAL]
  to send to the
  on-board equipment
  [SELF]
  a default gradient for TSR supervision, to be used for the parts of the track not covered by the gradient profile.
- kind: ordinary

##### 3.11.12.6 (Requirement Type)
The Default Gradient for TSR stored on-board shall be valid until a new Default Gradient for TSR is received.
- WordTraceId: 121831
- atomic: true
- Legal Obligation: mandatory
- implement: true
- implementerEnhanced: The Default Gradient for TSR stored on-board shall be valid
  until
  [TIME]
  a new Default Gradient for TSR is received.
- kind: ordinary

### 3.12 (Requirement Type)
Other Profiles
- WordTraceId: 121941
- atomic: false
- Legal Obligation: not applicable
- implement: false
- kind: Heading

#### 3.12.1 (Requirement Type)
Track Conditions
- WordTraceId: 121956
- atomic: false
- Legal Obligation: not applicable
- implement: false
- kind: Heading

##### 3.12.1.1 (Requirement Type)
The Track Condition function is used to inform the driver and/or the train of a condition in front of the train.
- WordTraceId: 121974
- atomic: true
- Legal Obligation: unknown
- implement: true
- implementerEnhanced: The Track Condition function is used to inform the
  driver
  [EXTERNAL]
  and/or the train of a condition in front of the train.
- kind: ordinary

##### 3.12.1.2 (Requirement Type)
A Track Condition shall be given as profile data (e.g. non-stopping area), i.e. start and end of the data is given, or location data (e.g. change of traction system) i.e. start location given, depending on the type of track condition.
- WordTraceId: 122088
- atomic: true
- Legal Obligation: mandatory
- implement: true
- implementerEnhanced: A Track Condition shall be given as profile data (
  e.g.
  [WEAK]
  non-stopping area), i.e. start and end of the data is given, or location data (
  e.g.
  [WEAK]
  change of traction system) i.e. start location given, depending on the type of track condition.
- kind: ordinary

###### 3.12.1.2.1 (Requirement Type)
The starting point of a profile type track condition shall be evaluated taking into account the max safe front end of the train, the end of the profile taking into account the min safe rear end of the train. Location type data shall be evaluated taking into account the max safe front of the train.
- WordTraceId: 122324
- atomic: false
- Legal Obligation: mandatory
- implement: true
- kind: ordinary

###### 3.12.1.2.1.1 (Requirement Type)
Note: The timing of output data to control train equipment (e.g. pantograph) is application specific.
- WordTraceId: 122623
- atomic: false
- Legal Obligation: not applicable
- implement: false
- implementerEnhanced: Note: The timing of output data to control train equipment (
  e.g.
  [WEAK]
  pantograph) is application specific.
- kind: Note

###### 3.12.1.2.1.2 (Requirement Type)
Exception 1: The starting point of a Big Metal Mass type track condition shall be evaluated taking into account the max safe
antenna
position, the end of the profile taking into account the min safe
antenna
position.
- WordTraceId: 122725
- atomic: true
- Legal Obligation: mandatory
- implement: true
- kind: ordinary

###### 3.12.1.2.1.3 (Requirement Type)
Exception 2: The end of the Powerless section shall be evaluated taking into account the min safe front end of the train.
- WordTraceId: 122942
- atomic: true
- Legal Obligation: mandatory
- implement: true
- kind: ordinary

###### 3.12.1.2.1.4 (Requirement Type)
Exception 3: The start and end of a tunnel stopping area and of a sound horn track condition shall be evaluated taking into account the estimated front end of the train.
- WordTraceId: 123064
- atomic: true
- Legal Obligation: mandatory
- implement: true
- kind: ordinary

##### 3.12.1.3 (Requirement Type)
The types of track conditions to be covered by this function are:
- WordTraceId: 123234
- atomic: true
- Legal Obligation: unknown
- implement: false
- kind: Heading

###### 3.12.1.3.*[1] (Requirement Type)
Powerless section, lower pantograph (initial state: no powerless section, i.e. pantograph not to be lowered)
- WordTraceId: 123300
- atomic: true
- Legal Obligation: unknown
- implement: true
- ListNumberText: ·
- kind: ordinary

###### 3.12.1.3.*[2] (Requirement Type)
Powerless section, switch off main power switch (initial state: no powerless section, i.e. main power switch not to be switched off)
- WordTraceId: 123409
- atomic: true
- Legal Obligation: unknown
- implement: true
- ListNumberText: ·
- kind: ordinary

###### 3.12.1.3.*[3] (Requirement Type)
Air tightness (initial state: no request for air tightness)
- WordTraceId: 123542
- atomic: true
- Legal Obligation: unknown
- implement: true
- ListNumberText: ·
- kind: ordinary

###### 3.12.1.3.*[4] (Requirement Type)
Sound horn (initial state: no request for sound horn)
- WordTraceId: 123602
- atomic: true
- Legal Obligation: unknown
- implement: true
- ListNumberText: ·
- kind: ordinary

###### 3.12.1.3.*[5] (Requirement Type)
Non stopping area (initial state: stopping permitted)
- WordTraceId: 123656
- atomic: true
- Legal Obligation: unknown
- implement: true
- ListNumberText: ·
- kind: ordinary

###### 3.12.1.3.*[6] (Requirement Type)
Tunnel stopping area (initial state: no tunnel stopping area)
- WordTraceId: 123710
- atomic: true
- Legal Obligation: unknown
- implement: true
- ListNumberText: ·
- kind: ordinary

###### 3.12.1.3.*[7] (Requirement Type)
Change of traction system, switch traction system on-board, used for train capable of handling several traction systems (initial state: no initial state – keep the current setting)
- WordTraceId: 123772
- atomic: true
- Legal Obligation: unknown
- implement: true
- ListNumberText: ·
- kind: ordinary

###### 3.12.1.3.*[8] (Requirement Type)
Change of allowed current consumption, limit current consumed by the train, used to adapt the maximum current consumption of the train to the maximum current allowed by the trackside (initial state: no initial state – keep the current setting)
- WordTraceId: 123953
- atomic: true
- Legal Obligation: unknown
- implement: true
- implementerEnhanced: Change of allowed current consumption, limit current consumed by the train, used to adapt the maximum current consumption of the train to the maximum current allowed by the
  trackside
  [EXTERNAL]
  (initial state: no initial state – keep the current setting)
- ListNumberText: ·
- kind: ordinary

###### 3.12.1.3.*[9] (Requirement Type)
Big metal masses, ignore onboard integrity check alarms of balise transmission. (initial state: alarms not ignored)
- WordTraceId: 124197
- atomic: true
- Legal Obligation: unknown
- implement: true
- implementerEnhanced: Big metal masses, ignore onboard integrity check alarms of
  balise
  [EXTERNAL]
  transmission. (initial state: alarms not ignored)
- ListNumberText: ·
- kind: ordinary

###### 3.12.1.3.*[10] (Requirement Type)
Radio hole, stop supervision of the loss of safe radio connection (initial state: loss of safe radio connection supervised)
- WordTraceId: 124313
- atomic: true
- Legal Obligation: unknown
- implement: true
- ListNumberText: ·
- kind: ordinary

###### 3.12.1.3.*[11] (Requirement Type)
Switch off regenerative brake (initial state: regenerative brake on)
- WordTraceId: 124437
- atomic: true
- Legal Obligation: unknown
- implement: true
- ListNumberText: ·
- kind: ordinary

###### 3.12.1.3.*[12] (Requirement Type)
Switch off eddy current brake for service brake (initial state: eddy current brake on for service brake)
- WordTraceId: 124506
- atomic: true
- Legal Obligation: unknown
- implement: true
- ListNumberText: ·
- kind: ordinary

###### 3.12.1.3.*[13] (Requirement Type)
Switch off eddy current brake for emergency brake (initial state: eddy current brake on for emergency brake)
- WordTraceId: 124611
- atomic: true
- Legal Obligation: unknown
- implement: true
- ListNumberText: ·
- kind: ordinary

###### 3.12.1.3.*[14] (Requirement Type)
Switch off magnetic shoe brake (initial state: magnetic shoe brake on).
- WordTraceId: 124720
- atomic: true
- Legal Obligation: unknown
- implement: true
- ListNumberText: ·
- kind: ordinary

###### 3.12.1.3.*[15] (Requirement Type)
Station platforms, enable passenger doors with or without steps according to platform location, side and height (initial state: not enabled).
- WordTraceId: 124792
- atomic: true
- Legal Obligation: unknown
- implement: true
- ListNumberText: ·
- kind: ordinary

###### 3.12.1.3.1 (Requirement Type)
Note: In case of regenerative brake switch off or magnetic shoe brake switch off, the deceleration of the emergency brake might be affected if the effect of these brakes was included in the calculation of the deceleration value
.
- WordTraceId: 124934
- atomic: false
- Legal Obligation: not applicable
- PlainText: Note: In case of regenerative brake switch off or magnetic shoe brake switch off, the deceleration of the emergency brake might be affected if the effect of these brakes was included in the calculation of the deceleration value.
- implement: false
- implementerEnhanced: Note:
  In case of
  [CONDITION]
  regenerative brake switch off or magnetic shoe brake switch off, the deceleration of the emergency brake might be affected
  if
  [CONDITION]
  the effect of these brakes was included in the calculation of the deceleration value.
- kind: Note

###### 3.12.1.3.2 (Requirement Type)
Note: In case of eddy current brake switch off the deceleration of the service brake or emergency brake might be affected if the effect of these brakes was included in the calculation of the deceleration value
.
- WordTraceId: 125163
- atomic: false
- Legal Obligation: not applicable
- PlainText: Note: In case of eddy current brake switch off the deceleration of the service brake or emergency brake might be affected if the effect of these brakes was included in the calculation of the deceleration value.
- implement: false
- implementerEnhanced: Note:
  In case of
  [CONDITION]
  eddy current brake switch off the deceleration of the service brake or emergency brake might be affected
  if
  [CONDITION]
  the effect of these brakes was included in the calculation of the deceleration value.
- kind: Note

###### 3.12.1.3.3 (Requirement Type)
Note: in case of powerless section the deceleration of the service brake or emergency brake might be affected if the effect of a regenerative brake not independent from the presence of voltage in the catenary was included in the calculation of the deceleration value.
- WordTraceId: 125374
- atomic: false
- Legal Obligation: not applicable
- implement: false
- implementerEnhanced: Note:
  in case of
  [CONDITION]
  powerless section the deceleration of the service brake or emergency brake might be affected
  if
  [CONDITION]
  the effect of a regenerative brake not independent from the presence of voltage in the catenary was included in the calculation of the deceleration value.
- kind: Note

##### 3.12.1.4 (Requirement Type)
Intentionally deleted.
- WordTraceId: 125642
- atomic: false
- Legal Obligation: not applicable
- implement: false
- kind: Placeholder

##### 3.12.1.5 (Requirement Type)
The following actions shall be performed at receiving a track condition:
- WordTraceId: 125665
- atomic: true
- Legal Obligation: not applicable
- implement: false
- kind: Heading

###### 3.12.1.5.a (Requirement Type)
Indicate on DMI (see chapter 5, procedure “Indication of track conditions”), except “Station platforms”, “Change of allowed current consumption” and “Big metal masses”.
- WordTraceId: 125738
- atomic: true
- Legal Obligation: mandatory
- implement: true
- ListNumberText: a)
- kind: ordinary

###### 3.12.1.5.b (Requirement Type)
Send information with the remaining distance to an ERTMS/ETCS external function, with the exception of big metal mass track condition, sound horn track condition, non stopping area, tunnel stopping area and supervision of radio transmission which are handled inside the ERTMS/ETCS on-board equipment.
- WordTraceId: 125907
- atomic: true
- Legal Obligation: mandatory
- implement: true
- implementerEnhanced: Send information with the remaining distance to an ERTMS/ETCS
  external
  [EXTERNAL]
  function, with the exception of big metal mass track condition, sound horn track condition, non stopping area, tunnel stopping area and supervision of radio transmission which are handled inside the
  ERTMS/ETCS on-board equipment
  [SELF]
  .
- ListNumberText: b)
- kind: ordinary

###### 3.12.1.5.1 (Requirement Type)
Note: Whether some information shall be filtered (not shown to the driver or not sent to an ERTMS/ETCS external function) is outside the scope of ERTMS/ETCS.
- WordTraceId: 126208
- atomic: false
- Legal Obligation: mandatory
- implement: false
- implementerEnhanced: Note:
  Whether
  [CONDITION]
  some information
  [WEAK]
  shall be filtered (not shown to the
  driver
  [EXTERNAL]
  or not sent to an ERTMS/ETCS
  external
  [EXTERNAL]
  function) is outside the scope of ERTMS/ETCS.
- kind: Note

###### 3.12.1.5.2 (Requirement Type)
Note: The ERTMS/ETCS external function must be able to handle new track condition of the same type as previously received and covering the same distance.
- WordTraceId: 126366
- atomic: false
- Legal Obligation: mandatory
- implement: false
- implementerEnhanced: Note: The ERTMS/ETCS
  external
  [EXTERNAL]
  function must be able to handle new track condition of the same type as previously received and covering the same distance.
- kind: Note

##### 3.12.1.6 (Requirement Type)
The train is permitted to run without any track condition information given from the trackside. The initial state shall then be used by the on-board equipment.
- WordTraceId: 126520
- atomic: false
- Legal Obligation: mandatory
- implement: true
- implementerEnhanced: The train is permitted to run without any track condition information given from the
  trackside
  [EXTERNAL]
  . The initial state shall then be used by the
  on-board equipment
  [SELF]
  .
- kind: ordinary

#### 3.12.2 (Requirement Type)
Route Suitability
- WordTraceId: 126680
- atomic: false
- Legal Obligation: not applicable
- implement: false
- kind: Heading

##### 3.12.2.1 (Requirement Type)
Route suitability data defines which values concerning loading gauge, traction system and axle load category a train must meet to be allowed to enter the route.
- WordTraceId: 126699
- atomic: true
- Legal Obligation: unknown
- implement: false
- kind: Definition

##### 3.12.2.2 (Requirement Type)
The route suitability data is sent as location data from the trackside when needed.
- WordTraceId: 126860
- atomic: true
- Legal Obligation: unknown
- implement: true
- implementerEnhanced: The route suitability data is sent as location data from the
  trackside
  [EXTERNAL]
  when
  [CONDITION]
  needed
  [WEAK]
  .
- kind: ordinary

##### 3.12.2.3 (Requirement Type)
On reception of route suitability data, the ERTMS/ETCS on-board equipment shall compare it with the corresponding Train Data stored on-board. Unsuitability exists if:
- WordTraceId: 126944
- atomic: false
- Legal Obligation: mandatory
- implement: true
- implementerEnhanced: On reception of route suitability data, the
  ERTMS/ETCS on-board equipment
  [SELF]
  shall compare it with the corresponding Train Data stored on-board. Unsuitability exists
  if
  [CONDITION]
  :
- kind: ordinary

###### 3.12.2.3.a (Requirement Type)
The loading gauge profile of the train is not included in the list of loading gauges accepted by trackside
- WordTraceId: 127111
- atomic: true
- Legal Obligation: unknown
- implement: true
- implementerEnhanced: The loading gauge profile of the train is not included in the list of loading gauges accepted by
  trackside
  [EXTERNAL]
- ListNumberText: a)
- kind: ordinary

###### 3.12.2.3.b (Requirement Type)
The list of traction systems accepted by the engine does not include the one received from trackside
- WordTraceId: 127218
- atomic: true
- Legal Obligation: unknown
- implement: true
- implementerEnhanced: The list of traction systems accepted by the engine does not include the one received from
  trackside
  [EXTERNAL]
- ListNumberText: b)
- kind: ordinary

###### 3.12.2.3.c (Requirement Type)
The axle load category of the train is higher than the permitted one received from trackside
- WordTraceId: 127319
- atomic: true
- Legal Obligation: unknown
- implement: true
- implementerEnhanced: The axle load category of the train is higher than the permitted one received from
  trackside
  [EXTERNAL]
- ListNumberText: c)
- kind: ordinary

##### 3.12.2.4 (Requirement Type)
If at least one unsuitability exists, the closest location corresponding to the unsuitability(ies) shall be considered as both the EOA and SvL (instead of the EOA and SvL given by the MA), with no Release Speed. The driver shall be informed about all unsuitabilities.
- WordTraceId: 127412
- atomic: false
- Legal Obligation: mandatory
- implement: true
- implementerEnhanced: If
  [CONDITION]
  at least
  [WEAK]
  one unsuitability exists, the closest location corresponding to the unsuitability(ies) shall be considered as both the EOA and SvL (instead of the EOA and SvL given by the MA), with no Release Speed. The
  driver
  [EXTERNAL]
  shall be informed about all unsuitabilities.
- kind: ordinary

##### 3.12.2.5 (Requirement Type)
Intentionally deleted.
- WordTraceId: 127680
- atomic: false
- Legal Obligation: not applicable
- implement: false
- kind: Placeholder

###### 3.12.2.5.1 (Requirement Type)
Intentionally deleted.
- WordTraceId: 127703
- atomic: false
- Legal Obligation: not applicable
- implement: false
- kind: Placeholder

##### 3.12.2.6 (Requirement Type)
Intentionally deleted.
- WordTraceId: 127726
- atomic: false
- Legal Obligation: not applicable
- implement: false
- kind: Placeholder

##### 3.12.2.7 (Requirement Type)
Intentionally deleted.
- WordTraceId: 127749
- atomic: false
- Legal Obligation: not applicable
- implement: false
- kind: Placeholder

##### 3.12.2.8 (Requirement Type)
If, for any reasons, the train overpasses the location of the first route suitability where incompatibility occurs, it shall be tripped.
- WordTraceId: 127772
- atomic: true
- Legal Obligation: mandatory
- implement: true
- implementerEnhanced: If
  [CONDITION]
  , for any reasons, the train overpasses the location of the first route suitability where incompatibility occurs, it shall be tripped.
- kind: ordinary

##### 3.12.2.9 (Requirement Type)
The Train Data concerning route suitability is part of the Train Data sent to the RBC.
- WordTraceId: 127909
- atomic: true
- Legal Obligation: unknown
- implement: true
- implementerEnhanced: The Train Data concerning route suitability is part of the Train Data sent to the
  RBC
  [EXTERNAL]
  .
- kind: ordinary

###### 3.12.2.9.1 (Requirement Type)
Note: This allows for route suitability supervision to be used in systems external to the ERTMS/ETCS system.
- WordTraceId: 127996
- atomic: false
- Legal Obligation: not applicable
- implement: false
- implementerEnhanced: Note: This allows for route suitability supervision to be used in systems
  external
  [EXTERNAL]
  to the ERTMS/ETCS system.
- kind: Note

##### 3.12.2.10 (Requirement Type)
The train is permitted to run without any route suitability data given from the track. No default values shall be used or supervised by the on-board equipment, i.e. the initial state is that no restrictions related to route suitability exists.
- WordTraceId: 128105
- atomic: false
- Legal Obligation: mandatory
- implement: true
- implementerEnhanced: The train is permitted to run without any route suitability data given from the track. No default values shall be used or supervised by the
  on-board equipment
  [SELF]
  , i.e. the initial state is that no restrictions related to route suitability exists.
- kind: ordinary

#### 3.12.3 (Requirement Type)
Text Transmission
- WordTraceId: 128349
- atomic: false
- Legal Obligation: not applicable
- implement: false
- kind: Heading

##### 3.12.3.1 (Requirement Type)
General Rules
- WordTraceId: 128367
- atomic: false
- Legal Obligation: not applicable
- implement: false
- kind: Heading

###### 3.12.3.1.1 (Requirement Type)
It shall be possible to transmit information to be displayed to the driver from the trackside to the on-board equipment in the form of text messages.
- WordTraceId: 128382
- atomic: true
- Legal Obligation: mandatory
- implement: true
- implementerEnhanced: It shall be possible to transmit information to be displayed to the
  driver
  [EXTERNAL]
  from the
  trackside
  [EXTERNAL]
  to the
  on-board equipment
  [SELF]
  in the form of text messages.
- kind: ordinary

###### 3.12.3.1.2 (Requirement Type)
Text messages shall always be supplemented by conditions on when and where they are to be displayed, and whether any acknowledgement is requested from the driver. These parameters shall be transmitted individually for each message.
- WordTraceId: 128533
- atomic: false
- Legal Obligation: mandatory
- implement: true
- implementerEnhanced: Text messages shall always be supplemented by conditions on
  when
  [CONDITION]
  and where they are to be displayed, and
  whether
  [CONDITION]
  any acknowledgement is requested from the
  driver
  [EXTERNAL]
  . These parameters shall be transmitted individually
  for each
  [LOOP]
  message.
- kind: ordinary

###### 3.12.3.1.3 (Requirement Type)
Text messages and the supplementary information shall always be transmitted in one message.
- WordTraceId: 128766
- atomic: true
- Legal Obligation: mandatory
- implement: true
- kind: ordinary

###### 3.12.3.1.4 (Requirement Type)
Text messages can contain the text to be displayed in plain text or a number selecting a fixed message.
- WordTraceId: 128859
- atomic: true
- Legal Obligation: unknown
- implement: true
- kind: ordinary

###### 3.12.3.1.4.1 (Requirement Type)
Note: In case of plain text messages the trackside selects the language in which the message is displayed.
- WordTraceId: 128963
- atomic: false
- Legal Obligation: not applicable
- implement: false
- implementerEnhanced: Note:
  In case of
  [CONDITION]
  plain text messages the
  trackside
  [EXTERNAL]
  selects the language in which the message is displayed.
- kind: Note

###### 3.12.3.1.5 (Requirement Type)
Intentionally deleted.
- WordTraceId: 129070
- atomic: false
- Legal Obligation: not applicable
- implement: false
- kind: Placeholder

###### 3.12.3.1.6 (Requirement Type)
Intentionally deleted.
- WordTraceId: 129093
- atomic: false
- Legal Obligation: not applicable
- implement: false
- kind: Placeholder

###### 3.12.3.1.7 (Requirement Type)
Intentionally deleted.
- WordTraceId: 129116
- atomic: false
- Legal Obligation: not applicable
- implement: false
- kind: Placeholder

###### 3.12.3.1.8 (Requirement Type)
Intentionally deleted.
- WordTraceId: 129139
- atomic: false
- Legal Obligation: not applicable
- implement: false
- kind: Placeholder

###### 3.12.3.1.9 (Requirement Type)
The following data shall be included in a text message:
- WordTraceId: 129162
- atomic: true
- Legal Obligation: not applicable
- implement: false
- kind: Heading

###### 3.12.3.1.9.*[1] (Requirement Type)
Class of message
- WordTraceId: 129219
- atomic: true
- Legal Obligation: mandatory
- implement: true
- ListNumberText: ·
- kind: ordinary

###### 3.12.3.1.9.*[2] (Requirement Type)
Plain text message or fixed message number
- WordTraceId: 129236
- atomic: true
- Legal Obligation: mandatory
- implement: true
- ListNumberText: ·
- kind: ordinary

###### 3.12.3.1.9.*[3] (Requirement Type)
Conditions for start of indication
- WordTraceId: 129279
- atomic: true
- Legal Obligation: mandatory
- implement: true
- ListNumberText: ·
- kind: ordinary

###### 3.12.3.1.9.*[4] (Requirement Type)
Conditions for end of indication
- WordTraceId: 129315
- atomic: true
- Legal Obligation: mandatory
- implement: true
- ListNumberText: ·
- kind: ordinary

###### 3.12.3.1.9.*[5] (Requirement Type)
If driver acknowledgement is requested or not
- WordTraceId: 129348
- atomic: true
- Legal Obligation: mandatory
- implement: true
- implementerEnhanced: If
  [CONDITION]
  driver
  [EXTERNAL]
  acknowledgement is requested or not
- ListNumberText: ·
- kind: ordinary

###### 3.12.3.1.10 (Requirement Type)
The appearance of a message shall depend on the class and on whether a driver acknowledgement is requested.
- WordTraceId: 129394
- atomic: true
- Legal Obligation: mandatory
- implement: true
- implementerEnhanced: The appearance of a message shall depend on the class and on
  whether
  [CONDITION]
  a
  driver
  [EXTERNAL]
  acknowledgement is requested.
- kind: ordinary

###### 3.12.3.1.11 (Requirement Type)
A text message from trackside may be sent with a request to report driver acknowledgement, if any, to an RBC.
- WordTraceId: 129502
- atomic: true
- Legal Obligation: optional
- implement: true
- implementerEnhanced: A text message from
  trackside
  [EXTERNAL]
  may be sent with a request to report
  driver
  [EXTERNAL]
  acknowledgement,
  if
  [CONDITION]
  any, to an
  RBC
  [EXTERNAL]
  .
- kind: ordinary

##### 3.12.3.2 (Requirement Type)
Text Message Classes
- WordTraceId: 129612
- atomic: false
- Legal Obligation: not applicable
- implement: false
- kind: Heading

###### 3.12.3.2.1 (Requirement Type)
Text messages shall be classified according to the following scheme:
- WordTraceId: 129633
- atomic: true
- Legal Obligation: mandatory
- implement: true
- kind: ordinary

###### 3.12.3.2.1[2] (Requirement Type)
- WordTraceId: 129702
- atomic: false
- Legal Obligation: not applicable
- implement: false
- kind: Placeholder

###### 3.12.3.2.1[2].[t]* (Requirement Type)
| Class | Characteristics/Appearance | Use |
| --- | --- | --- |
| [r][2].[c][1] Auxiliary Information | [r][2].[c][2] Displayed and deleted when specified conditions are met. May be hidden behind a message of another class. | [r][2].[c][3] Auxiliary operational information (e.g. station announcement etc.) |
| [r][3].[c][1] Important Information | [r][3].[c][2] Displayed and deleted when specified conditions are met. Shall never be hidden behind a message of another class. | [r][3].[c][3] Important operational information (e.g. information about workers on the line etc.). |
- WordTraceId: 130163
- atomic: false
- Legal Obligation: not applicable
- implement: false
- kind: Table

###### 3.12.3.2.1[2].[t]*.[r][2] (Requirement Type)
- WordTraceId: 129740
- atomic: false
- Legal Obligation: not applicable
- implement: false
- kind: Table

###### 3.12.3.2.1[2].[t]*.[r][2].[c][1] (Requirement Type)
Auxiliary Information
- WordTraceId: 129740
- atomic: true
- Legal Obligation: unknown
- implement: true
- kind: ordinary

###### 3.12.3.2.1[2].[t]*.[r][2].[c][2] (Requirement Type)
Displayed and deleted when specified conditions are met. May be hidden behind a message of another class.
- WordTraceId: 129762
- atomic: true
- Legal Obligation: optional
- implement: true
- implementerEnhanced: Displayed and deleted
  when
  [CONDITION]
  specified conditions are met. May be hidden behind a message of another class.
- kind: ordinary

###### 3.12.3.2.1[2].[t]*.[r][2].[c][3] (Requirement Type)
Auxiliary operational information (e.g. station announcement etc.)
- WordTraceId: 129870
- atomic: true
- Legal Obligation: unknown
- implement: true
- implementerEnhanced: Auxiliary operational information (
  e.g.
  [WEAK]
  station announcement
  etc.
  [WEAK]
  )
- kind: ordinary

###### 3.12.3.2.1[2].[t]*.[r][3] (Requirement Type)
- WordTraceId: 129938
- atomic: false
- Legal Obligation: not applicable
- implement: false
- kind: Table

###### 3.12.3.2.1[2].[t]*.[r][3].[c][1] (Requirement Type)
Important Information
- WordTraceId: 129938
- atomic: true
- Legal Obligation: unknown
- implement: true
- kind: ordinary

###### 3.12.3.2.1[2].[t]*.[r][3].[c][2] (Requirement Type)
Displayed and deleted when specified conditions are met. Shall never be hidden behind a message of another class.
- WordTraceId: 129960
- atomic: true
- Legal Obligation: mandatory
- implement: true
- implementerEnhanced: Displayed and deleted
  when
  [CONDITION]
  specified conditions are met. Shall never be hidden behind a message of another class.
- kind: ordinary

###### 3.12.3.2.1[2].[t]*.[r][3].[c][3] (Requirement Type)
Important operational information (e.g. information about workers on the line etc.).
- WordTraceId: 130077
- atomic: true
- Legal Obligation: unknown
- implement: true
- implementerEnhanced: Important operational information (
  e.g.
  [WEAK]
  information about workers on the line
  etc.
  [WEAK]
  ).
- kind: ordinary

##### 3.12.3.3 (Requirement Type)
Fixed text messages
- WordTraceId: 130163
- atomic: false
- Legal Obligation: not applicable
- implement: false
- kind: Heading

###### 3.12.3.3.1 (Requirement Type)
Fixed text messages shall be stored on-board in all languages that can be selected by the driver.
- WordTraceId: 130183
- atomic: true
- Legal Obligation: mandatory
- implement: true
- implementerEnhanced: Fixed text messages shall be stored on-board in all languages that can be selected by the
  driver
  [EXTERNAL]
  .
- kind: ordinary

###### 3.12.3.3.2 (Requirement Type)
Intentionally deleted.
- WordTraceId: 130281
- atomic: false
- Legal Obligation: not applicable
- implement: false
- kind: Placeholder

###### 3.12.3.3.3 (Requirement Type)
Intentionally deleted.
- WordTraceId: 130304
- atomic: false
- Legal Obligation: not applicable
- implement: false
- kind: Placeholder

###### 3.12.3.3.4 (Requirement Type)
Intentionally deleted.
- WordTraceId: 130327
- atomic: false
- Legal Obligation: not applicable
- implement: false
- kind: Placeholder

###### 3.12.3.3.5 (Requirement Type)
Intentionally deleted.
- WordTraceId: 130350
- atomic: false
- Legal Obligation: not applicable
- implement: false
- kind: Placeholder

##### 3.12.3.4 (Requirement Type)
Conditions for Start/End of Indication
- WordTraceId: 130373
- atomic: false
- Legal Obligation: not applicable
- implement: false
- kind: Heading

###### 3.12.3.4.1 (Requirement Type)
It shall be possible to specify individual events for start/end condition of indication.
- WordTraceId: 130412
- atomic: true
- Legal Obligation: mandatory
- implement: true
- kind: ordinary

###### 3.12.3.4.2 (Requirement Type)
The following events can be used to define the start condition:
- WordTraceId: 130503
- atomic: true
- Legal Obligation: unknown
- implement: false
- kind: Heading

###### 3.12.3.4.2.*[1] (Requirement Type)
Location
- WordTraceId: 130568
- atomic: true
- Legal Obligation: unknown
- implement: true
- ListNumberText: ·
- kind: ordinary

###### 3.12.3.4.2.*[2] (Requirement Type)
Mode (start display as soon as in mode)
- WordTraceId: 130578
- atomic: true
- Legal Obligation: unknown
- implement: true
- implementerEnhanced: Mode (start display
  as soon as
  [WEAK]
  in mode)
- ListNumberText: ·
- kind: ordinary

###### 3.12.3.4.2.*[3] (Requirement Type)
Level (start display as soon as in level)
- WordTraceId: 130619
- atomic: true
- Legal Obligation: unknown
- implement: true
- implementerEnhanced: Level (start display
  as soon as
  [WEAK]
  in level)
- ListNumberText: ·
- kind: ordinary

###### 3.12.3.4.3 (Requirement Type)
The following events can be used to define the end condition:
- WordTraceId: 130662
- atomic: true
- Legal Obligation: unknown
- implement: false
- kind: Heading

###### 3.12.3.4.3.*[1] (Requirement Type)
Location
- WordTraceId: 130724
- atomic: true
- Legal Obligation: unknown
- implement: true
- ListNumberText: ·
- kind: ordinary

###### 3.12.3.4.3.*[2] (Requirement Type)
Time
- WordTraceId: 130734
- atomic: true
- Legal Obligation: unknown
- implement: true
- implementerEnhanced: Time
  [TIME]
- ListNumberText: ·
- kind: ordinary

###### 3.12.3.4.3.*[3] (Requirement Type)
Mode (stop display when leaving mode)
- WordTraceId: 130739
- atomic: true
- Legal Obligation: unknown
- implement: true
- implementerEnhanced: Mode (stop display
  when
  [CONDITION]
  leaving mode)
- ListNumberText: ·
- kind: ordinary

###### 3.12.3.4.3.*[4] (Requirement Type)
Level (stop display when leaving level)
- WordTraceId: 130777
- atomic: true
- Legal Obligation: unknown
- implement: true
- implementerEnhanced: Level (stop display
  when
  [CONDITION]
  leaving level)
- ListNumberText: ·
- kind: ordinary

###### 3.12.3.4.3.1 (Requirement Type)
It shall be possible to define whether one or all of the events used from the list in 3.12.3.4.2/3.12.3.4.3 have to be fulfilled to define the start/end condition. This definition shall apply to both start and end conditions.
- WordTraceId: 130817
- atomic: false
- Legal Obligation: mandatory
- implement: true
- implementerEnhanced: It shall be possible to define
  whether
  [CONDITION]
  one or all of the events used from the list in 3.12.3.4.2/3.12.3.4.3 have to be fulfilled to define the start/end condition. This definition shall apply to both start and end conditions.
- kind: ordinary
- CrossRefLink -> 3.12.3.4.2
- CrossRefLink -> 3.12.3.4.3

###### 3.12.3.4.3.2 (Requirement Type)
In case a confirmation of the text message is requested, it shall be possible to define whether the driver acknowledgement is considered:
- WordTraceId: 131043
- atomic: true
- Legal Obligation: mandatory
- implement: true
- implementerEnhanced: In case
  [CONDITION]
  a confirmation of the text message is requested, it shall be possible to define
  whether
  [CONDITION]
  the
  driver
  [EXTERNAL]
  acknowledgement is considered:
- kind: ordinary

###### 3.12.3.4.3.2.a (Requirement Type)
As always ending the text display, regardless of the end condition defined in 3.12.3.4.3.1
- WordTraceId: 131181
- atomic: true
- Legal Obligation: unknown
- implement: true
- ListNumberText: a)
- kind: ordinary
- CrossRefLink -> 3.12.3.4.3.1

###### 3.12.3.4.3.2.b (Requirement Type)
As a necessary condition to end the text display, in addition to the end condition defined in 3.12.3.4.3.1.
- WordTraceId: 131272
- atomic: true
- Legal Obligation: unknown
- implement: true
- ListNumberText: b)
- kind: ordinary
- CrossRefLink -> 3.12.3.4.3.1

###### 3.12.3.4.4 (Requirement Type)
The end condition shall be evaluated as soon as the start condition is fulfilled. No display shall take place if the end condition is immediately fulfilled.
- WordTraceId: 131380
- atomic: false
- Legal Obligation: mandatory
- implement: true
- implementerEnhanced: The end condition shall be evaluated
  as soon as
  [WEAK]
  the start condition is fulfilled. No display shall take place
  if
  [CONDITION]
  the end condition is
  immediately
  [WEAK]
  fulfilled.
- kind: ordinary

###### 3.12.3.4.5 (Requirement Type)
Once the text message is displayed and the end condition is fulfilled, the start condition shall not be re-evaluated.
- WordTraceId: 131537
- atomic: true
- Legal Obligation: mandatory
- implement: true
- implementerEnhanced: Once the text message is displayed and the end condition is fulfilled, the start condition shall not be
  re-evaluated
  [AGAIN]
  .
- kind: ordinary

###### 3.12.3.4.6 (Requirement Type)
When the end event "location" is used, the length on which the text is displayed shall refer to the location used for the start condition, independently from other start events.
- WordTraceId: 131655
- atomic: true
- Legal Obligation: mandatory
- implement: true
- implementerEnhanced: When
  [CONDITION]
  the end event "location" is used, the length on which the text is displayed shall refer to the location used for the start condition, independently from other start events.
- kind: ordinary

###### 3.12.3.4.7 (Requirement Type)
In case a confirmation of the text message is requested, it shall be possible to define whether the service brake or emergency brake application shall be commanded if the driver does not acknowledge before the end condition is fulfilled..
- WordTraceId: 131833
- atomic: false
- Legal Obligation: mandatory
- implement: true
- implementerEnhanced: In case
  [CONDITION]
  a confirmation of the text message is requested, it shall be possible to define
  whether
  [CONDITION]
  the service brake or emergency brake application shall be commanded
  if
  [CONDITION]
  the
  driver
  [EXTERNAL]
  does not acknowledge before the end condition is fulfilled..
- kind: ordinary

###### 3.12.3.4.7.1 (Requirement Type)
If the driver does not acknowledge before the end condition is fulfilled, the text message shall remain displayed until acknowledged by driver.
- WordTraceId: 132073
- atomic: true
- Legal Obligation: mandatory
- implement: true
- implementerEnhanced: If
  [CONDITION]
  the
  driver
  [EXTERNAL]
  does not acknowledge before the end condition is fulfilled, the text message shall remain displayed
  until
  [TIME]
  acknowledged by
  driver
  [EXTERNAL]
  .
- kind: ordinary

###### 3.12.3.4.7.2 (Requirement Type)
If the driver acknowledges before the end condition is fulfilled, the on-board equipment shall consider the driver acknowledgement as requested by trackside (see 3.12.3.4.3.2).
- WordTraceId: 132217
- atomic: true
- Legal Obligation: mandatory
- implement: true
- implementerEnhanced: If
  [CONDITION]
  the
  driver
  [EXTERNAL]
  acknowledges before the end condition is fulfilled, the
  on-board equipment
  [SELF]
  shall consider the
  driver
  [EXTERNAL]
  acknowledgement as requested by
  trackside
  [EXTERNAL]
  (see 3.12.3.4.3.2).
- kind: ordinary
- CrossRefLink -> 3.12.3.4.3.2

###### 3.12.3.4.8 (Requirement Type)
Intentionally deleted.
- WordTraceId: 132394
- atomic: false
- Legal Obligation: not applicable
- implement: false
- kind: Placeholder

##### 3.12.3.5 (Requirement Type)
Report of driver acknowledgement to RBC
- WordTraceId: 132417
- atomic: false
- Legal Obligation: not applicable
- implement: false
- implementerEnhanced: Report of
  driver
  [EXTERNAL]
  acknowledgement to
  RBC
  [EXTERNAL]
- kind: Heading

###### 3.12.3.5.1 (Requirement Type)
If trackside requests a report of driver acknowledgement, then it shall include:
- WordTraceId: 132457
- atomic: true
- Legal Obligation: mandatory
- implement: true
- implementerEnhanced: If
  [CONDITION]
  trackside
  [EXTERNAL]
  requests a report of
  driver
  [EXTERNAL]
  acknowledgement, then it shall include:
- kind: ordinary

###### 3.12.3.5.1.*[1] (Requirement Type)
a text message identifier
- WordTraceId: 132538
- atomic: true
- Legal Obligation: unknown
- implement: true
- ListNumberText: ·
- kind: ordinary

###### 3.12.3.5.1.*[2] (Requirement Type)
the identity of the RBC to which the driver acknowledgement report is to be sent.
- WordTraceId: 132564
- atomic: true
- Legal Obligation: unknown
- implement: true
- implementerEnhanced: the identity of the
  RBC
  [EXTERNAL]
  to which the
  driver
  [EXTERNAL]
  acknowledgement report is to be sent.
- ListNumberText: ·
- kind: ordinary

###### 3.12.3.5.2 (Requirement Type)
When the driver has acknowledged a text message with a request to report driver acknowledgement, the driver acknowledgement report, including the text message identifier, shall be sent to the RBC referenced in the request.
- WordTraceId: 132646
- atomic: true
- Legal Obligation: mandatory
- implement: true
- implementerEnhanced: When
  [CONDITION]
  the
  driver
  [EXTERNAL]
  has acknowledged a text message with a request to report
  driver
  [EXTERNAL]
  acknowledgement, the
  driver
  [EXTERNAL]
  acknowledgement report, including the text message identifier, shall be sent to the
  RBC
  [EXTERNAL]
  referenced in the request.
- kind: ordinary

###### 3.12.3.5.3 (Requirement Type)
A new text message with request for report of driver acknowledgement shall be rejected by the ERTMS/ETCS on-board equipment if it has the same text message identifier as a previously received text message, which the driver has not yet acknowledged.
- WordTraceId: 132869
- atomic: true
- Legal Obligation: mandatory
- implement: true
- implementerEnhanced: A new text message with request for report of
  driver
  [EXTERNAL]
  acknowledgement shall be rejected by the
  ERTMS/ETCS on-board equipment
  [SELF]
  if
  [CONDITION]
  it has the same text message identifier as a previously received text message, which the
  driver
  [EXTERNAL]
  has
  not yet
  [TIME]
  acknowledged.
- kind: ordinary

#### 3.12.4 (Requirement Type)
Mode profile
- WordTraceId: 133118
- atomic: false
- Legal Obligation: not applicable
- implement: false
- kind: Heading

##### 3.12.4.1 (Requirement Type)
The Mode Profile can request On Sight mode, Limited Supervision mode and Shunting mode.
- WordTraceId: 133132
- atomic: true
- Legal Obligation: unknown
- implement: true
- kind: ordinary

##### 3.12.4.2 (Requirement Type)
For OS and LS mode the mode profile shall define the entry and the length of the On Sight/Limited Supervision area. For SH mode the mode profile only defines the entry location to SH mode, any length given shall be ignored by the on-board.
- WordTraceId: 133220
- atomic: false
- Legal Obligation: mandatory
- implement: false
- kind: Definition

##### 3.12.4.3 (Requirement Type)
On reception of a new MA (with or without Mode Profile) the on-board equipment shall delete the currently supervised Mode Profile.
- WordTraceId: 133461
- atomic: true
- Legal Obligation: mandatory
- implement: true
- implementerEnhanced: On reception of a new MA (with or without Mode Profile) the
  on-board equipment
  [SELF]
  shall delete the currently supervised Mode Profile.
- kind: ordinary

###### 3.12.4.3.1 (Requirement Type)
Exception: When receiving a new MA by infill, any currently supervised Mode Profile shall be deleted only beyond the reference location of the infill information.
- WordTraceId: 133592
- atomic: true
- Legal Obligation: mandatory
- implement: true
- implementerEnhanced: Exception:
  When
  [CONDITION]
  receiving a new MA by infill, any currently supervised Mode Profile shall be deleted only beyond the reference location of the infill information.
- kind: ordinary

##### 3.12.4.4 (Requirement Type)
In case the mode profile information for shunting is overwritten by a new shunting profile, before the on-board equipment switches to SH mode, a previous list of balise groups for SH area shall be deleted or replaced by a new list of balise groups for SH area.
- WordTraceId: 133755
- atomic: true
- Legal Obligation: mandatory
- implement: true
- implementerEnhanced: In case
  [CONDITION]
  the mode profile information for shunting is overwritten by a new shunting profile, before the
  on-board equipment
  [SELF]
  switches to SH mode, a previous list of
  balise groups
  [EXTERNAL]
  for SH area shall be deleted or replaced by a new list of
  balise groups
  [EXTERNAL]
  for SH area.
- kind: ordinary

##### 3.12.4.5 (Requirement Type)
The beginning of the Mode Profile relates to the max safe front end of the train.
- WordTraceId: 134016
- atomic: true
- Legal Obligation: unknown
- implement: true
- kind: ordinary

##### 3.12.4.6 (Requirement Type)
The end of the mode profile relates to the min safe front end of the train.
- WordTraceId: 134098
- atomic: true
- Legal Obligation: unknown
- implement: true
- kind: ordinary

#### 3.12.5 (Requirement Type)
Level Crossings
- WordTraceId: 134174
- atomic: false
- Legal Obligation: not applicable
- implement: false
- kind: Heading

##### 3.12.5.1 (Requirement Type)
It shall be possible for trackside to inform the ERTMS/ETCS on-board equipment about the conditions under which a Level Crossing (LX) must be passed.
- WordTraceId: 134190
- atomic: true
- Legal Obligation: mandatory
- implement: true
- implementerEnhanced: It shall be possible for
  trackside
  [EXTERNAL]
  to inform the
  ERTMS/ETCS on-board equipment
  [SELF]
  about the conditions under which a Level Crossing (LX) must be passed.
- kind: ordinary

##### 3.12.5.2 (Requirement Type)
Each Level Crossing shall have an identity, so that all LX information shall be independent of each other. This means that an individual LX information shall not affect, nor be affected by, any other individual LX information.
- WordTraceId: 134340
- atomic: false
- Legal Obligation: mandatory
- implement: true
- kind: ordinary

##### 3.12.5.3 (Requirement Type)
If the ERTMS/ETCS on-board equipment receives a new LX information with the same identity as an already received LX information, the new LX information shall replace the previous one.
- WordTraceId: 134567
- atomic: true
- Legal Obligation: mandatory
- implement: true
- implementerEnhanced: If
  [CONDITION]
  the
  ERTMS/ETCS on-board equipment
  [SELF]
  receives a new LX information with the same identity as an already received LX information, the new LX information shall replace the previous one.
- kind: ordinary

##### 3.12.5.4 (Requirement Type)
Level Crossing information shall be given as profile data, corresponding to the LX start location and the length of the LX area.
- WordTraceId: 134751
- atomic: true
- Legal Obligation: mandatory
- implement: true
- kind: ordinary

##### 3.12.5.5 (Requirement Type)
Level Crossing information shall indicate whether the LX is protected or not.
- WordTraceId: 134880
- atomic: true
- Legal Obligation: mandatory
- implement: true
- implementerEnhanced: Level Crossing information shall indicate
  whether
  [CONDITION]
  the LX is protected or not.
- kind: ordinary

##### 3.12.5.6 (Requirement Type)
In case the LX is not protected, ERTMS/ETCS on-board equipment shall be informed:
- WordTraceId: 134958
- atomic: true
- Legal Obligation: mandatory
- implement: true
- implementerEnhanced: In case
  [CONDITION]
  the LX is not protected,
  ERTMS/ETCS on-board equipment
  [SELF]
  shall be informed:
- kind: ordinary

###### 3.12.5.6.a (Requirement Type)
at which speed the LX is allowed to be passed
- WordTraceId: 135040
- atomic: true
- Legal Obligation: unknown
- implement: true
- ListNumberText: a)
- kind: ordinary

###### 3.12.5.6.b (Requirement Type)
whether the stopping of the train in rear of the LX start location is required or not
- WordTraceId: 135086
- atomic: true
- Legal Obligation: unknown
- implement: true
- implementerEnhanced: whether
  [CONDITION]
  the stopping of the train in rear of the LX start location is required or not
- ListNumberText: b)
- kind: ordinary

##### 3.12.5.7 (Requirement Type)
In case stopping in rear of the non protected LX is required, a stopping area in rear of the LX start location shall be defined.
- WordTraceId: 135172
- atomic: true
- Legal Obligation: mandatory
- implement: true
- implementerEnhanced: In case
  [CONDITION]
  stopping in rear of the non protected LX is required, a stopping area in rear of the LX start location shall be defined.
- kind: ordinary

### 3.13 (Requirement Type)
Speed and distance monitoring
- WordTraceId: 135301
- atomic: false
- Legal Obligation: not applicable
- implement: false
- kind: Heading

#### 3.13.1 (Requirement Type)
Introduction
- WordTraceId: 135331
- atomic: false
- Legal Obligation: not applicable
- implement: false
- kind: Heading

##### 3.13.1.1 (Requirement Type)
The speed and distance monitoring is the supervision of the speed of the train versus its position, in order to assure that the train remains within the given speed and distance limits.
- WordTraceId: 135344
- atomic: true
- Legal Obligation: unknown
- implement: true
- kind: ordinary

###### 3.13.1.1.1 (Requirement Type)
Note: The speed and distance monitoring of the on-board can only assure this when the following necessary conditions are fulfilled:
- WordTraceId: 135530
- atomic: false
- Legal Obligation: not applicable
- implement: false
- implementerEnhanced: Note: The speed and distance monitoring of the on-board can only assure this
  when
  [CONDITION]
  the following necessary conditions are fulfilled:
- kind: Note

###### 3.13.1.1.1.*[1] (Requirement Type)
Brake system of the train functions as specified
- WordTraceId: 135662
- atomic: true
- Legal Obligation: unknown
- implement: false
- ListNumberText: ·
- kind: Note

###### 3.13.1.1.1.*[2] (Requirement Type)
wheel/rail adhesion is sufficient for the required safe deceleration
- WordTraceId: 135711
- atomic: true
- Legal Obligation: unknown
- implement: false
- ListNumberText: ·
- kind: Note

###### 3.13.1.1.1.*[3] (Requirement Type)
Brake characteristics (and other Train Data) are correctly entered into the on-board (automatic or by driver)
- WordTraceId: 135780
- atomic: true
- Legal Obligation: unknown
- implement: false
- implementerEnhanced: Brake characteristics (and other Train Data) are correctly entered into the on-board (automatic or by
  driver
  [EXTERNAL]
  )
- ListNumberText: ·
- kind: Note

##### 3.13.1.2 (Requirement Type)
Note: The ERTMS/ETCS on-board equipment triggers brake commands and revokes them, it may also receive status information if the brakes are applied or released. However, it cannot be made responsible if brake control circuits outside the equipment fail. Also the way the brakes are released by the driver after a revocation of a brake command is an implementation issue.
- WordTraceId: 135890
- atomic: false
- Legal Obligation: optional
- implement: false
- implementerEnhanced: Note: The
  ERTMS/ETCS on-board equipment
  [SELF]
  triggers brake commands and revokes them, it may also receive status information
  if
  [CONDITION]
  the brakes are applied or released. However, it cannot be made responsible
  if
  [CONDITION]
  brake control circuits outside the equipment fail. Also the way the brakes are released by the
  driver
  [EXTERNAL]
  after
  [TIME]
  a revocation of a brake command is an implementation issue.
- kind: Note

##### 3.13.1.3 (Requirement Type)
Figure 28
gives an overview of the main elements contributing to the speed and distance monitoring. These elements (inputs, functions and outputs) are detailed in the following chapters.
- WordTraceId: 136260
- atomic: false
- Legal Obligation: unknown
- implement: true
- kind: ordinary
- CrossRefLink -> 3.13.1.3[2].[f]28.C

##### 3.13.1.3[2] (Requirement Type)
- WordTraceId: 136473
- atomic: false
- Legal Obligation: not applicable
- implement: false
- kind: Placeholder

###### 3.13.1.3[2].[f]28 (Requirement Type)
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- WordTraceId: 136501
- atomic: false
- Legal Obligation: not applicable
- implement: false
- kind: Figure

###### 3.13.1.3[2].[f]28.C (Requirement Type)
Figure {Figure 28}: Speed and distance monitoring overview
- WordTraceId: 136501
- atomic: true
- Legal Obligation: unknown
- PlainText: Figure 28: Speed and distance monitoring overview
- implement: false
- kind: Figure

##### 3.13.1.4 (Requirement Type)
Throughout the following sections, all the distances marked with “d” (lower case), which are referred in parameters, formulas and figures, are counted from the current reference location of the on-board equipment (e.g. the LRBG).
- WordTraceId: 136576
- atomic: true
- Legal Obligation: unknown
- implement: false
- implementerEnhanced: Throughout the following sections, all the distances marked with “d” (lower case), which are referred in parameters, formulas and figures, are counted from the current reference location of the
  on-board equipment
  [SELF]
  (
  e.g.
  [WEAK]
  the
  LRBG
  [EXTERNAL]
  ).
- kind: Definition

#### 3.13.2 (Requirement Type)
Inputs for speed and distance monitoring
- WordTraceId: 136806
- atomic: false
- Legal Obligation: not applicable
- implement: false
- kind: Heading

##### 3.13.2.1 (Requirement Type)
Introduction
- WordTraceId: 136847
- atomic: false
- Legal Obligation: not applicable
- implement: false
- kind: Heading

###### 3.13.2.1.1 (Requirement Type)
The traction / braking models, the brake position / brake percentage are used for the definition of the kinematic behaviour of the train after a service brake command or an emergency brake command has been initiated.
- WordTraceId: 136860
- atomic: true
- Legal Obligation: unknown
- implement: true
- implementerEnhanced: The traction / braking models, the brake position / brake percentage are used for the definition of the kinematic behaviour of the train
  after
  [TIME]
  a service brake command or an emergency brake command has been initiated.
- kind: ordinary

###### 3.13.2.1.2 (Requirement Type)
However, railway brakes have a statistical behaviour and braking distances vary within the typical distribution for a given condition. Correction factors are therefore incorporated for the speed and distance monitoring.
- WordTraceId: 137077
- atomic: false
- Legal Obligation: unknown
- implement: true
- kind: ordinary

###### 3.13.2.1.3 (Requirement Type)
The correction factors will allow obtaining, from the nominal emergency braking performance of the train, the minimum emergency braking performances that are required for reference conditions set by trackside.
- WordTraceId: 137297
- atomic: true
- Legal Obligation: unknown
- implement: true
- implementerEnhanced: The correction factors will allow obtaining, from the nominal emergency braking performance of the train, the minimum emergency braking performances that are required for reference conditions set by
  trackside
  [EXTERNAL]
  .
- kind: ordinary

##### 3.13.2.2 (Requirement Type)
Train related inputs
- WordTraceId: 137507
- atomic: false
- Legal Obligation: not applicable
- implement: false
- kind: Heading

###### 3.13.2.2.1 (Requirement Type)
Introduction
- WordTraceId: 137528
- atomic: false
- Legal Obligation: not applicable
- implement: false
- kind: Heading

###### 3.13.2.2.1.1 (Requirement Type)
The train related inputs to be considered for the speed and distance monitoring are:
- WordTraceId: 137541
- atomic: true
- Legal Obligation: unknown
- implement: false
- kind: Heading

###### 3.13.2.2.1.1.a (Requirement Type)
Traction model
- WordTraceId: 137626
- atomic: true
- Legal Obligation: unknown
- implement: true
- ListNumberText: a)
- kind: ordinary

###### 3.13.2.2.1.1.b (Requirement Type)
Braking models (brake build up time and speed dependent deceleration) or brake percentage
- WordTraceId: 137641
- atomic: true
- Legal Obligation: unknown
- implement: true
- implementerEnhanced: Braking models (brake build up
  time
  [TIME]
  and speed dependent deceleration) or brake percentage
- ListNumberText: b)
- kind: ordinary

###### 3.13.2.2.1.1.c (Requirement Type)
Brake position
- WordTraceId: 137731
- atomic: true
- Legal Obligation: unknown
- implement: true
- ListNumberText: c)
- kind: ordinary

###### 3.13.2.2.1.1.d (Requirement Type)
Special brakes
- WordTraceId: 137746
- atomic: true
- Legal Obligation: unknown
- implement: true
- ListNumberText: d)
- kind: ordinary

###### 3.13.2.2.1.1.e (Requirement Type)
Service brake interface
- WordTraceId: 137761
- atomic: true
- Legal Obligation: unknown
- implement: true
- ListNumberText: e)
- kind: ordinary

###### 3.13.2.2.1.1.f (Requirement Type)
Traction cut-off interface
- WordTraceId: 137785
- atomic: true
- Legal Obligation: unknown
- implement: true
- ListNumberText: f)
- kind: ordinary

###### 3.13.2.2.1.1.g (Requirement Type)
On-board correction factors
- WordTraceId: 137812
- atomic: true
- Legal Obligation: unknown
- implement: true
- ListNumberText: g)
- kind: ordinary

###### 3.13.2.2.1.1.h (Requirement Type)
Nominal rotating mass
- WordTraceId: 137840
- atomic: true
- Legal Obligation: unknown
- implement: true
- ListNumberText: h)
- kind: ordinary

###### 3.13.2.2.1.1.i (Requirement Type)
Train length
- WordTraceId: 137862
- atomic: true
- Legal Obligation: unknown
- implement: true
- ListNumberText: i)
- kind: ordinary

###### 3.13.2.2.1.1.j (Requirement Type)
Fixed values related to speed and distance monitoring
- WordTraceId: 137875
- atomic: true
- Legal Obligation: unknown
- implement: true
- ListNumberText: j)
- kind: ordinary

###### 3.13.2.2.1.1.k (Requirement Type)
Train related speed restriction (i.e. the maximum train speed)
- WordTraceId: 137929
- atomic: true
- Legal Obligation: unknown
- implement: true
- ListNumberText: k)
- kind: ordinary

###### 3.13.2.2.1.2 (Requirement Type)
All train related inputs except the fixed values are acquired as Train Data (see 3.18.3.2 items b) c) and d)).
- WordTraceId: 137993
- atomic: true
- Legal Obligation: unknown
- implement: true
- kind: ordinary
- CrossRefLink -> 3.18.3.2.b
- CrossRefLink -> 3.18.3.2.c
- CrossRefLink -> 3.18.3.2.d

###### 3.13.2.2.1.3 (Requirement Type)
The speed and distance monitoring shall use braking models acquired as Train Data, unless the brake percentage is acquired as Train Data and the conversion model is applicable (see 3.13.3.2 for its validity limits).
- WordTraceId: 138104
- atomic: true
- Legal Obligation: mandatory
- implement: true
- kind: ordinary
- CrossRefLink -> 3.13.3.2

###### 3.13.2.2.2 (Requirement Type)
Traction model
- WordTraceId: 138320
- atomic: false
- Legal Obligation: not applicable
- implement: false
- kind: Heading

###### 3.13.2.2.2.1 (Requirement Type)
The traction model shall be given as a step function as indicated in Figure 29. It shall describe the time delay T_traction_cut_off from the traction cut-off command by the on-board (t0) to the moment the acceleration due to traction (A_traction) is guaranteed to be zero (t1). The estimated acceleration value of the train shall be considered during this time delay.
- WordTraceId: 138335
- atomic: false
- Legal Obligation: mandatory
- implement: true
- implementerEnhanced: The traction model shall be given as a step function as indicated in Figure 29. It shall describe the
  time delay
  [TIME]
  T_traction_cut_off from the traction cut-off command by the on-board (t0) to the moment the acceleration due to traction (A_traction) is guaranteed to be zero (t1). The estimated acceleration value of the train shall be considered
  during
  [TIME]
  this
  time delay
  [TIME]
  .
- kind: ordinary
- CrossRefLink -> 3.13.2.2.2.1[2].[f]29.C

###### 3.13.2.2.2.1[2] (Requirement Type)
- WordTraceId: 138745
- atomic: false
- Legal Obligation: not applicable
- implement: false
- kind: Placeholder

###### 3.13.2.2.2.1[2].[f]29 (Requirement Type)
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- WordTraceId: 138773
- atomic: false
- Legal Obligation: not applicable
- implement: false
- kind: Figure

###### 3.13.2.2.2.1[2].[f]29.C (Requirement Type)
Figure {Figure 29}: Traction Model
- WordTraceId: 138773
- atomic: true
- Legal Obligation: unknown
- PlainText: Figure 29: Traction Model
- implement: false
- implementerEnhanced: Figure 29: Traction Model
- kind: Figure

###### 3.13.2.2.2.2 (Requirement Type)
Note: The current value of A_traction is not known directly by the on-board. It is implicitly known as a contribution to the estimated acceleration, together with the acceleration due to gradient.
- WordTraceId: 138824
- atomic: false
- Legal Obligation: not applicable
- implement: false
- kind: Note

###### 3.13.2.2.3 (Requirement Type)
Braking Models
- WordTraceId: 139021
- atomic: false
- Legal Obligation: not applicable
- implement: false
- kind: Heading

###### 3.13.2.2.3.1 (Requirement Type)
Speed Dependent Deceleration
- WordTraceId: 139036
- atomic: false
- Legal Obligation: not applicable
- implement: false
- kind: Heading

###### 3.13.2.2.3.1.1 (Requirement Type)
The deceleration due to braking shall be given as a step function of the speed.
- WordTraceId: 139065
- atomic: true
- Legal Obligation: mandatory
- implement: true
- kind: ordinary

###### 3.13.2.2.3.1.2 (Requirement Type)
It shall be possible to define up to seven steps for each speed dependent deceleration model.
- WordTraceId: 139145
- atomic: true
- Legal Obligation: mandatory
- implement: true
- implementerEnhanced: It shall be possible to define up to seven steps
  for each
  [LOOP]
  speed dependent deceleration model.
- kind: ordinary

###### 3.13.2.2.3.1.3 (Requirement Type)
Note: An example with 4 steps is given in Figure 30. A_brake(V) is calculated as follows:
- WordTraceId: 139239
- atomic: false
- Legal Obligation: not applicable
- implement: false
- kind: Note
- CrossRefLink -> 3.13.2.2.3.1.3[2].[f]30.C

###### 3.13.2.2.3.1.3.*[1] (Requirement Type)
A_brake = AD_0 when 0 ≤ speed ≤ V1
- WordTraceId: 139355
- atomic: true
- Legal Obligation: unknown
- PlainText: A_brake = AD_0  when 0 ≤ speed ≤ V1
- implement: false
- implementerEnhanced: A_brake = AD_0
  when
  [CONDITION]
  0 ≤ speed ≤ V1
- ListNumberText: ·
- kind: Note

###### 3.13.2.2.3.1.3.*[2] (Requirement Type)
A_brake = AD_1 when V1 < speed ≤ V2
- WordTraceId: 139391
- atomic: true
- Legal Obligation: unknown
- PlainText: A_brake = AD_1  when V1 < speed ≤ V2
- implement: false
- implementerEnhanced: A_brake = AD_1
  when
  [CONDITION]
  V1 < speed ≤ V2
- ListNumberText: ·
- kind: Note

###### 3.13.2.2.3.1.3.*[3] (Requirement Type)
A_brake = AD_2 when V2 < speed ≤ V3
- WordTraceId: 139428
- atomic: true
- Legal Obligation: unknown
- PlainText: A_brake = AD_2  when V2 < speed ≤ V3
- implement: false
- implementerEnhanced: A_brake = AD_2
  when
  [CONDITION]
  V2 < speed ≤ V3
- ListNumberText: ·
- kind: Note

###### 3.13.2.2.3.1.3.*[4] (Requirement Type)
A_brake = AD_3 when V3 < speed
- WordTraceId: 139465
- atomic: true
- Legal Obligation: unknown
- PlainText: A_brake = AD_3  when V3 < speed
- implement: false
- implementerEnhanced: A_brake = AD_3
  when
  [CONDITION]
  V3 < speed
- ListNumberText: ·
- kind: Note

###### 3.13.2.2.3.1.3[2] (Requirement Type)
- WordTraceId: 139497
- atomic: false
- Legal Obligation: not applicable
- implement: false
- kind: Placeholder

###### 3.13.2.2.3.1.3[2].[f]30 (Requirement Type)
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- WordTraceId: 139525
- atomic: false
- Legal Obligation: not applicable
- implement: false
- kind: Figure

###### 3.13.2.2.3.1.3[2].[f]30.C (Requirement Type)
Figure {Figure 30}: Speed Dependent Deceleration Model
- WordTraceId: 139525
- atomic: true
- Legal Obligation: unknown
- PlainText: Figure 30: Speed Dependent Deceleration Model
- implement: false
- kind: Figure

###### 3.13.2.2.3.1.4 (Requirement Type)
The last step of A_brake(V) shall by definition be considered as open ended, i.e. it has no upper speed limit.
- WordTraceId: 139596
- atomic: true
- Legal Obligation: mandatory
- implement: false
- kind: Definition

###### 3.13.2.2.3.1.5 (Requirement Type)
The model shall be applicable only after full build up of the braking effort (see a_full in Figure 31)
- WordTraceId: 139707
- atomic: true
- Legal Obligation: mandatory
- implement: true
- implementerEnhanced: The model shall be applicable only
  after
  [TIME]
  full build up of the braking effort (see a_full in Figure 31)
- kind: ordinary
- CrossRefLink -> 3.13.2.2.3.2.2[2].[f]31.C

###### 3.13.2.2.3.1.6 (Requirement Type)
The model shall be used for the emergency brake nominal deceleration (A_brake_emergency(V)), for the full service brake deceleration (A_brake_service(V)) and for the normal service brake deceleration (A_brake_normal_service(V)).
- WordTraceId: 139836
- atomic: true
- Legal Obligation: mandatory
- implement: true
- kind: ordinary

###### 3.13.2.2.3.1.7 (Requirement Type)
It shall be possible to define individual speed dependent deceleration models of A_brake_emergency(V) and A_brake_service(V) for each combination of use of regenerative brake, eddy current brake and magnetic shoe brake.
- WordTraceId: 140065
- atomic: true
- Legal Obligation: mandatory
- implement: true
- implementerEnhanced: It shall be possible to define individual speed dependent deceleration models of A_brake_emergency(V) and A_brake_service(V)
  for each
  [LOOP]
  combination of use of regenerative brake, eddy current brake and magnetic shoe brake.
- kind: ordinary

###### 3.13.2.2.3.1.8 (Requirement Type)
Note: Individual deceleration models may be equal, thereby avoiding the influence of a specific brake on A_brake_emergency(V) or A_brake_service(V). However, the choice to take into account or not the contribution of a specific brake for A_brake_emergency(V) or A_brake_service(V) is only rolling stock dependent, not an ETCS implementation issue.
- WordTraceId: 140285
- atomic: false
- Legal Obligation: optional
- implement: false
- kind: Note

###### 3.13.2.2.3.1.9 (Requirement Type)
It shall be possible to define up to two sets of three models of A_brake_normal_service(V):
- WordTraceId: 140633
- atomic: true
- Legal Obligation: mandatory
- implement: true
- kind: ordinary

###### 3.13.2.2.3.1.9.a (Requirement Type)
one set applicable when the brake position is in “Freight train in G”
- WordTraceId: 140725
- atomic: true
- Legal Obligation: unknown
- implement: true
- implementerEnhanced: one set applicable
  when
  [CONDITION]
  the brake position is in “Freight train in G”
- ListNumberText: a)
- kind: ordinary

###### 3.13.2.2.3.1.9.b (Requirement Type)
one set applicable when the brake position is in “Passenger train in P” or “Freight train in P”
- WordTraceId: 140795
- atomic: true
- Legal Obligation: unknown
- implement: true
- implementerEnhanced: one set applicable
  when
  [CONDITION]
  the brake position is in “Passenger train in P” or “Freight train in P”
- ListNumberText: b)
- kind: ordinary

###### 3.13.2.2.3.1.10 (Requirement Type)
A set of A_brake_normal_service(V) shall be defined as a function of the full service brake deceleration at zero speed, A_brake_service(V=0):
- WordTraceId: 140891
- atomic: true
- Legal Obligation: mandatory
- implement: false
- kind: Definition

###### 3.13.2.2.3.1.10[2] (Requirement Type)
If A_brake_service(V = 0) ≤ A_SB01
- WordTraceId: 141033
- atomic: true
- Legal Obligation: unknown
- implement: true
- implementerEnhanced: If
  [CONDITION]
  A_brake_service(V = 0) ≤ A_SB01
- kind: ordinary

###### 3.13.2.2.3.1.10[3] (Requirement Type)
A_brake_normal_service(V) = A_brake_normal_service_0(V)
- WordTraceId: 141068
- atomic: true
- Legal Obligation: unknown
- implement: true
- kind: ordinary

###### 3.13.2.2.3.1.10[4] (Requirement Type)
if A_SB01 < A_brake_service(V = 0) ≤ A_SB12
- WordTraceId: 141124
- atomic: true
- Legal Obligation: unknown
- implement: true
- implementerEnhanced: if
  [CONDITION]
  A_SB01 < A_brake_service(V = 0) ≤ A_SB12
- kind: ordinary

###### 3.13.2.2.3.1.10[5] (Requirement Type)
A_brake_normal_service(V) = A_brake_normal_service_1(V)
- WordTraceId: 141168
- atomic: true
- Legal Obligation: unknown
- implement: true
- kind: ordinary

###### 3.13.2.2.3.1.10[6] (Requirement Type)
if A_SB12 < A_brake_service (V = 0)
- WordTraceId: 141224
- atomic: true
- Legal Obligation: unknown
- implement: true
- implementerEnhanced: if
  [CONDITION]
  A_SB12 < A_brake_service (V = 0)
- kind: ordinary

###### 3.13.2.2.3.1.10[7] (Requirement Type)
A_brake_normal_service(V) = A_brake_normal_service_2(V)
- WordTraceId: 141260
- atomic: true
- Legal Obligation: unknown
- implement: true
- kind: ordinary

###### 3.13.2.2.3.1.11 (Requirement Type)
Note: the two pivot values A_SB01 and A_SB12 are part of the A_brake_normal_service model, i.e. they are train related input data for the speed and distance monitoring function.
- WordTraceId: 141316
- atomic: false
- Legal Obligation: not applicable
- implement: false
- kind: Note

###### 3.13.2.2.3.2 (Requirement Type)
Brake build up time
- WordTraceId: 141494
- atomic: false
- Legal Obligation: not applicable
- implement: false
- implementerEnhanced: Brake build up
  time
  [TIME]
- kind: Heading

###### 3.13.2.2.3.2.1 (Requirement Type)
The deceleration A_brake is not available immediately after the on-board commands the brake. There is a time lag between brake command and the start of the brake force build-up. There is also time needed to build up the full brake force.
- WordTraceId: 141514
- atomic: false
- Legal Obligation: unknown
- implement: true
- implementerEnhanced: The deceleration A_brake is not available
  immediately
  [WEAK]
  after
  [TIME]
  the on-board commands the brake. There is a
  time
  [TIME]
  lag between brake command and the start of the brake force build-up. There is also
  time
  [TIME]
  needed to build up the full brake force.
- kind: ordinary

###### 3.13.2.2.3.2.2 (Requirement Type)
The model for the brake build up time shall be given as a step function as explained in Figure 31.
- WordTraceId: 141752
- atomic: true
- Legal Obligation: mandatory
- implement: true
- implementerEnhanced: The model for the brake build up
  time
  [TIME]
  shall be given as a step function as explained in Figure 31.
- kind: ordinary
- CrossRefLink -> 3.13.2.2.3.2.2[2].[f]31.C

###### 3.13.2.2.3.2.2[2] (Requirement Type)
- WordTraceId: 141877
- atomic: false
- Legal Obligation: not applicable
- implement: false
- kind: Placeholder

###### 3.13.2.2.3.2.2[2].[f]31 (Requirement Type)
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- WordTraceId: 141905
- atomic: false
- Legal Obligation: not applicable
- implement: false
- kind: Figure

###### 3.13.2.2.3.2.2[2].[f]31.C (Requirement Type)
Figure {Figure 31}: Brake Build Up Time Model
- WordTraceId: 141905
- atomic: true
- Legal Obligation: unknown
- PlainText: Figure 31: Brake Build Up Time Model
- implement: false
- implementerEnhanced: Figure 31: Brake Build Up
  Time
  [TIME]
  Model
- kind: Figure

###### 3.13.2.2.3.2.3 (Requirement Type)
In Figure 31, the following time intervals are defined:
- WordTraceId: 141967
- atomic: true
- Legal Obligation: unknown
- implement: false
- implementerEnhanced: In Figure 31, the following
  time
  [TIME]
  intervals are defined:
- kind: Heading
- CrossRefLink -> 3.13.2.2.3.2.2[2].[f]31.C

###### 3.13.2.2.3.2.3.a (Requirement Type)
T_brake_react (t0…t1) is the interval between the command of the brake by the on-board and the moment the brake force starts to build up.
- WordTraceId: 142049
- atomic: true
- Legal Obligation: unknown
- implement: false
- ListNumberText: a)
- kind: Definition

###### 3.13.2.2.3.2.3.b (Requirement Type)
T_brake_increase (t1...t2) is the interval in which the brake force increases from the zero to the moment when 95% of full brake power is reached.
- WordTraceId: 142187
- atomic: true
- Legal Obligation: unknown
- implement: false
- implementerEnhanced: T_brake_increase (t1
  ...
  [WEAK]
  t2) is the interval in which the brake force increases from the zero to the moment
  when
  [CONDITION]
  95% of full brake power is reached.
- ListNumberText: b)
- kind: Definition

###### 3.13.2.2.3.2.3.c (Requirement Type)
T_brake_build_up (t0...t3) is the equivalent brake build up time.
- WordTraceId: 142334
- atomic: true
- Legal Obligation: unknown
- implement: false
- implementerEnhanced: T_brake_build_up (t0
  ...
  [WEAK]
  t3) is the equivalent brake build up
  time
  [TIME]
  .
- ListNumberText: c)
- kind: Definition

###### 3.13.2.2.3.2.4 (Requirement Type)
The equivalent brake build up time (T_brake_build_up) is defined as T_brake_build_up = T_brake_react + 0.5*T_brake_increase.
- WordTraceId: 142400
- atomic: true
- Legal Obligation: unknown
- implement: false
- implementerEnhanced: The equivalent brake build up
  time
  [TIME]
  (T_brake_build_up) is defined as T_brake_build_up = T_brake_react + 0.5*T_brake_increase.
- kind: Definition

###### 3.13.2.2.3.2.5 (Requirement Type)
This model for T_brake_build_up shall be used for the emergency brake (T_brake_emergency) and for the full service brake (T_brake_service).
- WordTraceId: 142525
- atomic: true
- Legal Obligation: mandatory
- implement: true
- kind: ordinary

###### 3.13.2.2.3.2.6 (Requirement Type)
Note: The equivalent brake build up time is a safe approximation. In the beginning of the build-up time the model assumes a smaller deceleration, in the later part this is compensated by a higher deceleration.
- WordTraceId: 142665
- atomic: false
- Legal Obligation: not applicable
- implement: false
- implementerEnhanced: Note: The equivalent brake build up
  time
  [TIME]
  is a safe approximation. In the beginning of the build-up
  time
  [TIME]
  the model assumes a smaller deceleration, in the later part this is compensated by a higher deceleration.
- kind: Note

###### 3.13.2.2.3.2.7 (Requirement Type)
Note: T_brake_react and T_brake_increase are indicated in Figure 31 for completeness reasons; only T_brake_build_up is to be considered as an input for the speed and distance monitoring function.
- WordTraceId: 142875
- atomic: false
- Legal Obligation: not applicable
- implement: false
- kind: Note
- CrossRefLink -> 3.13.2.2.3.2.2[2].[f]31.C

###### 3.13.2.2.3.2.8 (Requirement Type)
It shall be possible to define individual values of T_brake_emergency and T_brake_service for each combination of use of regenerative brake, eddy current brake, magnetic shoe brake and Ep brake.
- WordTraceId: 143097
- atomic: true
- Legal Obligation: mandatory
- implement: true
- implementerEnhanced: It shall be possible to define individual values of T_brake_emergency and T_brake_service
  for each
  [LOOP]
  combination of use of regenerative brake, eddy current brake, magnetic shoe brake and Ep brake.
- kind: ordinary

###### 3.13.2.2.3.2.9 (Requirement Type)
Note: Individual values of T_brake_emergency and T_brake_service may be equal, thereby avoiding the influence of a specific brake. However, the choice to take into account or not the contribution of a specific brake for T_brake_emergency and T_brake_service is only rolling stock dependent, not an ETCS implementation issue.
- WordTraceId: 143292
- atomic: false
- Legal Obligation: optional
- implement: false
- kind: Note

###### 3.13.2.2.3.2.10 (Requirement Type)
Note: In general, T_brake_emergency and T_brake_service are determined by the pneumatic brake therefore avoiding to take into account of the influence of the regenerative brake, eddy current brake or magnetic shoe brake. However, if the Electro-pneumatic brake system is used, it is possible that T_brake_emergency and T_brake_service are determined by another special brake.
- WordTraceId: 143617
- atomic: false
- Legal Obligation: not applicable
- implement: false
- implementerEnhanced: Note: In general, T_brake_emergency and T_brake_service are determined by the pneumatic brake therefore avoiding to take into account of the influence of the regenerative brake, eddy current brake or magnetic shoe brake. However,
  if
  [CONDITION]
  the Electro-pneumatic brake system is used, it is possible that T_brake_emergency and T_brake_service are determined by another special brake.
- kind: Note

###### 3.13.2.2.4 (Requirement Type)
Brake Position
- WordTraceId: 143993
- atomic: false
- Legal Obligation: not applicable
- implement: false
- kind: Heading

###### 3.13.2.2.4.1 (Requirement Type)
The brake position shall be set to one of the following three values:
- WordTraceId: 144008
- atomic: true
- Legal Obligation: mandatory
- implement: true
- kind: ordinary

###### 3.13.2.2.4.1.a (Requirement Type)
Passenger train in P
- WordTraceId: 144078
- atomic: true
- Legal Obligation: mandatory (== 1)
- implement: true
- implementerEnhanced: Passenger train in P
  [LINKED_PHRASE]
- ListNumberText: a)
- kind: ordinary
- KnownTermLink -> 3.13.2.2.3.1.9.b

###### 3.13.2.2.4.1.b (Requirement Type)
Freight train in P
- WordTraceId: 144099
- atomic: true
- Legal Obligation: mandatory (== 1)
- implement: true
- implementerEnhanced: Freight train in P
  [LINKED_PHRASE]
- ListNumberText: b)
- kind: ordinary
- KnownTermLink -> 3.13.2.2.3.1.9.b

###### 3.13.2.2.4.1.c (Requirement Type)
Freight train in G
- WordTraceId: 144118
- atomic: true
- Legal Obligation: mandatory (== 1)
- implement: true
- implementerEnhanced: Freight train in G
  [LINKED_PHRASE]
- ListNumberText: c)
- kind: ordinary
- KnownTermLink -> 3.13.2.2.3.1.9.a

###### 3.13.2.2.4.2 (Requirement Type)
Note: The brake position defines the behaviour of the brake for specific train types.
- WordTraceId: 144137
- atomic: false
- Legal Obligation: not applicable
- implement: false
- kind: Note

###### 3.13.2.2.5 (Requirement Type)
Brake Percentage
- WordTraceId: 144223
- atomic: false
- Legal Obligation: not applicable
- implement: false
- kind: Heading

###### 3.13.2.2.5.1 (Requirement Type)
If the brake percentage is captured as Train Data and the conversion model is applicable (see 3.13.3.2), they are used to derive A_brake_emergency(V), A_brake_service(V), T_brake_emergency and T_brake_service.
- WordTraceId: 144240
- atomic: true
- Legal Obligation: unknown
- implement: true
- implementerEnhanced: If
  [CONDITION]
  the brake percentage is captured as Train Data and the conversion model is applicable (see 3.13.3.2), they are used to derive A_brake_emergency(V), A_brake_service(V), T_brake_emergency and T_brake_service.
- kind: ordinary
- CrossRefLink -> 3.13.3.2

###### 3.13.2.2.5.2 (Requirement Type)
Note: the conversion model has been designed assuming that all the provisions laid down in the UIC leaflet 544-1, with the exception of sections 9.1.2 and 9.2.2, apply for the acquired brake percentage.
- WordTraceId: 144479
- atomic: false
- Legal Obligation: not applicable
- implement: false
- kind: Note

###### 3.13.2.2.6 (Requirement Type)
Special Brakes
- WordTraceId: 144683
- atomic: false
- Legal Obligation: not applicable
- implement: false
- kind: Heading

###### 3.13.2.2.6.1 (Requirement Type)
For each special brake (regenerative brake, eddy current brake, magnetic shoe brake and electro-pneumatic brake), it shall be possible to configure the on-board to one of the following possibilities marked with an “X” in Table 3
- WordTraceId: 144698
- atomic: true
- Legal Obligation: mandatory
- implement: true
- implementerEnhanced: For each
  [LOOP]
  special brake (regenerative brake, eddy current brake, magnetic shoe brake and electro-pneumatic brake), it shall be possible to configure the on-board to one of the following possibilities marked with an “X” in Table 3
- kind: ordinary
- CrossRefLink -> 3.13.2.2.6.1[2].[t]3.C

###### 3.13.2.2.6.1[2] (Requirement Type)
- WordTraceId: 144953
- atomic: false
- Legal Obligation: not applicable
- implement: false
- kind: Placeholder

###### 3.13.2.2.6.1[2].[t]3 (Requirement Type)
|  |  | configuration possibilities |  |  |  |
| --- | --- | --- | --- | --- | --- |
|  |  | No interface exists | Interface exists and status affects the emergency brake model only | Interface exists and status affects the service brake model only | Interface exists and status affects both emergency and service brake models |
| [r][3].[c][1] Special brake | [r][3].[c][2] regenerative brake | [r][3].[c][3] x | [r][3].[c][4] x | [r][3].[c][5] x | [r][3].[c][6] x |
| [r][3].[c][1] Special brake | [r][4].[c][2] eddy current brake | [r][4].[c][3] x | [r][4].[c][4] x | [r][4].[c][5] x | [r][4].[c][6] x |
| [r][3].[c][1] Special brake | [r][5].[c][2] magnetic shoe brake | [r][5].[c][3] x | [r][5].[c][4] x | [r][5].[c][5] | [r][5].[c][6] |
| [r][3].[c][1] Special brake | [r][6].[c][2] Ep brake | [r][6].[c][3] x | [r][6].[c][4] | [r][6].[c][5] x | [r][6].[c][6] x |
- WordTraceId: 145332
- atomic: false
- Legal Obligation: not applicable
- implement: false
- kind: Table

###### 3.13.2.2.6.1[2].[t]3.C (Requirement Type)
Table {Table 3}: On-board Configuration in relation to special brakes
- WordTraceId: 145332
- atomic: true
- Legal Obligation: unknown
- PlainText: Table 3: On-board Configuration in relation to special brakes
- implement: false
- kind: Table

###### 3.13.2.2.6.1[2].[t]3.[r][3] (Requirement Type)
- WordTraceId: 145215
- atomic: false
- Legal Obligation: not applicable
- implement: false
- kind: Table

###### 3.13.2.2.6.1[2].[t]3.[r][3].[c][1] (Requirement Type)
Special brake
- WordTraceId: 145215
- atomic: true
- Legal Obligation: unknown
- implement: true
- kind: ordinary

###### 3.13.2.2.6.1[2].[t]3.[r][3].[c][2] (Requirement Type)
regenerative brake
- WordTraceId: 145229
- atomic: true
- Legal Obligation: unknown
- implement: true
- kind: ordinary

###### 3.13.2.2.6.1[2].[t]3.[r][3].[c][3] (Requirement Type)
x
- WordTraceId: 145248
- atomic: true
- Legal Obligation: unknown
- implement: true
- kind: ordinary

###### 3.13.2.2.6.1[2].[t]3.[r][3].[c][4] (Requirement Type)
x
- WordTraceId: 145250
- atomic: true
- Legal Obligation: unknown
- implement: true
- kind: ordinary

###### 3.13.2.2.6.1[2].[t]3.[r][3].[c][5] (Requirement Type)
x
- WordTraceId: 145252
- atomic: true
- Legal Obligation: unknown
- implement: true
- kind: ordinary

###### 3.13.2.2.6.1[2].[t]3.[r][3].[c][6] (Requirement Type)
x
- WordTraceId: 145254
- atomic: true
- Legal Obligation: unknown
- implement: true
- kind: ordinary

###### 3.13.2.2.6.1[2].[t]3.[r][4] (Requirement Type)
- WordTraceId: 145257
- atomic: false
- Legal Obligation: not applicable
- implement: false
- kind: Table

###### 3.13.2.2.6.1[2].[t]3.[r][4].[c][2] (Requirement Type)
eddy current brake
- WordTraceId: 145258
- atomic: true
- Legal Obligation: unknown
- implement: true
- kind: ordinary

###### 3.13.2.2.6.1[2].[t]3.[r][4].[c][3] (Requirement Type)
x
- WordTraceId: 145277
- atomic: true
- Legal Obligation: unknown
- implement: true
- kind: ordinary

###### 3.13.2.2.6.1[2].[t]3.[r][4].[c][4] (Requirement Type)
x
- WordTraceId: 145279
- atomic: true
- Legal Obligation: unknown
- implement: true
- kind: ordinary

###### 3.13.2.2.6.1[2].[t]3.[r][4].[c][5] (Requirement Type)
x
- WordTraceId: 145281
- atomic: true
- Legal Obligation: unknown
- implement: true
- kind: ordinary

###### 3.13.2.2.6.1[2].[t]3.[r][4].[c][6] (Requirement Type)
x
- WordTraceId: 145283
- atomic: true
- Legal Obligation: unknown
- implement: true
- kind: ordinary

###### 3.13.2.2.6.1[2].[t]3.[r][5] (Requirement Type)
- WordTraceId: 145286
- atomic: false
- Legal Obligation: not applicable
- implement: false
- kind: Table

###### 3.13.2.2.6.1[2].[t]3.[r][5].[c][2] (Requirement Type)
magnetic shoe brake
- WordTraceId: 145287
- atomic: true
- Legal Obligation: unknown
- implement: true
- kind: ordinary

###### 3.13.2.2.6.1[2].[t]3.[r][5].[c][3] (Requirement Type)
x
- WordTraceId: 145307
- atomic: true
- Legal Obligation: unknown
- implement: true
- kind: ordinary

###### 3.13.2.2.6.1[2].[t]3.[r][5].[c][4] (Requirement Type)
x
- WordTraceId: 145309
- atomic: true
- Legal Obligation: unknown
- implement: true
- kind: ordinary

###### 3.13.2.2.6.1[2].[t]3.[r][5].[c][5] (Requirement Type)
- WordTraceId: 145311
- atomic: true
- Legal Obligation: unknown
- implement: true
- kind: ordinary

###### 3.13.2.2.6.1[2].[t]3.[r][5].[c][6] (Requirement Type)
- WordTraceId: 145312
- atomic: true
- Legal Obligation: unknown
- implement: true
- kind: ordinary

###### 3.13.2.2.6.1[2].[t]3.[r][6] (Requirement Type)
- WordTraceId: 145314
- atomic: false
- Legal Obligation: not applicable
- implement: false
- kind: Table

###### 3.13.2.2.6.1[2].[t]3.[r][6].[c][2] (Requirement Type)
Ep brake
- WordTraceId: 145315
- atomic: true
- Legal Obligation: unknown
- implement: true
- kind: ordinary

###### 3.13.2.2.6.1[2].[t]3.[r][6].[c][3] (Requirement Type)
x
- WordTraceId: 145324
- atomic: true
- Legal Obligation: unknown
- implement: true
- kind: ordinary

###### 3.13.2.2.6.1[2].[t]3.[r][6].[c][4] (Requirement Type)
- WordTraceId: 145326
- atomic: true
- Legal Obligation: unknown
- implement: true
- kind: ordinary

###### 3.13.2.2.6.1[2].[t]3.[r][6].[c][5] (Requirement Type)
x
- WordTraceId: 145327
- atomic: true
- Legal Obligation: unknown
- implement: true
- kind: ordinary

###### 3.13.2.2.6.1[2].[t]3.[r][6].[c][6] (Requirement Type)
x
- WordTraceId: 145329
- atomic: true
- Legal Obligation: unknown
- implement: true
- kind: ordinary

###### 3.13.2.2.6.2 (Requirement Type)
When an interface exists with the regenerative brake, eddy current brake, magnetic shoe brake system and/or the Ep brake on-board system and depending whether their status affects the concerned brake parameter(s), the speed and distance monitoring shall take into account their status “active” or “not active” to select the appropriate brake parameter(s) captured as Train Data, according to Table 4:
- WordTraceId: 145418
- atomic: true
- Legal Obligation: mandatory
- implement: true
- implementerEnhanced: When
  [CONDITION]
  an interface exists with the regenerative brake, eddy current brake, magnetic shoe brake system and/or the Ep brake on-board system and depending
  whether
  [CONDITION]
  their status affects the concerned brake parameter(s), the speed and distance monitoring shall take into account their status “active” or “not active” to select the appropriate brake parameter(s) captured as Train Data, according to Table 4:
- kind: ordinary
- CrossRefLink -> 3.13.2.2.6.2[2].[t]4.C

###### 3.13.2.2.6.2[2] (Requirement Type)
- WordTraceId: 145845
- atomic: false
- Legal Obligation: not applicable
- implement: false
- kind: Placeholder

###### 3.13.2.2.6.2[2].[t]4 (Requirement Type)
|  |  | When interface exists and if status affects the brake parameter, selection of brake parameter according to status of: |  |  |  |
| --- | --- | --- | --- | --- | --- |
|  |  | regenerative brake | eddy current brake | magnetic shoe brake | Ep brake |
| [r][3].[c][1] Brake parameter | [r][3].[c][2] A_brake_emergency(V) | [r][3].[c][3] x | [r][3].[c][4] x | [r][3].[c][5] x | [r][3].[c][6] |
| [r][3].[c][1] Brake parameter | [r][4].[c][2] T_brake_emergency | [r][4].[c][3] x | [r][4].[c][4] x | [r][4].[c][5] x | [r][4].[c][6] x |
| [r][3].[c][1] Brake parameter | [r][5].[c][2] A_brake_service(V) | [r][5].[c][3] x | [r][5].[c][4] x | [r][5].[c][5] | [r][5].[c][6] |
| [r][3].[c][1] Brake parameter | [r][6].[c][2] T_brake_service | [r][6].[c][3] x | [r][6].[c][4] x | [r][6].[c][5] | [r][6].[c][6] x |
- WordTraceId: 146162
- atomic: false
- Legal Obligation: not applicable
- implement: false
- kind: Table

###### 3.13.2.2.6.2[2].[t]4.C (Requirement Type)
Table {Table 4}: Selection of brake parameters according to status of special brakes
- WordTraceId: 146162
- atomic: true
- Legal Obligation: unknown
- PlainText: Table 4: Selection of brake parameters according to status of special brakes
- implement: false
- kind: Table

###### 3.13.2.2.6.2[2].[t]4.[r][3] (Requirement Type)
- WordTraceId: 146036
- atomic: false
- Legal Obligation: not applicable
- implement: false
- kind: Table

###### 3.13.2.2.6.2[2].[t]4.[r][3].[c][1] (Requirement Type)
Brake parameter
- WordTraceId: 146036
- atomic: true
- Legal Obligation: unknown
- implement: true
- kind: ordinary

###### 3.13.2.2.6.2[2].[t]4.[r][3].[c][2] (Requirement Type)
A_brake_emergency(V)
- WordTraceId: 146053
- atomic: true
- Legal Obligation: unknown
- implement: true
- kind: ordinary

###### 3.13.2.2.6.2[2].[t]4.[r][3].[c][3] (Requirement Type)
x
- WordTraceId: 146074
- atomic: true
- Legal Obligation: unknown
- implement: true
- kind: ordinary

###### 3.13.2.2.6.2[2].[t]4.[r][3].[c][4] (Requirement Type)
x
- WordTraceId: 146076
- atomic: true
- Legal Obligation: unknown
- implement: true
- kind: ordinary

###### 3.13.2.2.6.2[2].[t]4.[r][3].[c][5] (Requirement Type)
x
- WordTraceId: 146078
- atomic: true
- Legal Obligation: unknown
- implement: true
- kind: ordinary

###### 3.13.2.2.6.2[2].[t]4.[r][3].[c][6] (Requirement Type)
- WordTraceId: 146080
- atomic: true
- Legal Obligation: unknown
- implement: true
- kind: ordinary

###### 3.13.2.2.6.2[2].[t]4.[r][4] (Requirement Type)
- WordTraceId: 146082
- atomic: false
- Legal Obligation: not applicable
- implement: false
- kind: Table

###### 3.13.2.2.6.2[2].[t]4.[r][4].[c][2] (Requirement Type)
T_brake_emergency
- WordTraceId: 146083
- atomic: true
- Legal Obligation: unknown
- implement: true
- kind: ordinary

###### 3.13.2.2.6.2[2].[t]4.[r][4].[c][3] (Requirement Type)
x
- WordTraceId: 146101
- atomic: true
- Legal Obligation: unknown
- implement: true
- kind: ordinary

###### 3.13.2.2.6.2[2].[t]4.[r][4].[c][4] (Requirement Type)
x
- WordTraceId: 146103
- atomic: true
- Legal Obligation: unknown
- implement: true
- kind: ordinary

###### 3.13.2.2.6.2[2].[t]4.[r][4].[c][5] (Requirement Type)
x
- WordTraceId: 146105
- atomic: true
- Legal Obligation: unknown
- implement: true
- kind: ordinary

###### 3.13.2.2.6.2[2].[t]4.[r][4].[c][6] (Requirement Type)
x
- WordTraceId: 146107
- atomic: true
- Legal Obligation: unknown
- implement: true
- kind: ordinary

###### 3.13.2.2.6.2[2].[t]4.[r][5] (Requirement Type)
- WordTraceId: 146110
- atomic: false
- Legal Obligation: not applicable
- implement: false
- kind: Table

###### 3.13.2.2.6.2[2].[t]4.[r][5].[c][2] (Requirement Type)
A_brake_service(V)
- WordTraceId: 146111
- atomic: true
- Legal Obligation: unknown
- implement: true
- kind: ordinary

###### 3.13.2.2.6.2[2].[t]4.[r][5].[c][3] (Requirement Type)
x
- WordTraceId: 146130
- atomic: true
- Legal Obligation: unknown
- implement: true
- kind: ordinary

###### 3.13.2.2.6.2[2].[t]4.[r][5].[c][4] (Requirement Type)
x
- WordTraceId: 146132
- atomic: true
- Legal Obligation: unknown
- implement: true
- kind: ordinary

###### 3.13.2.2.6.2[2].[t]4.[r][5].[c][5] (Requirement Type)
- WordTraceId: 146134
- atomic: true
- Legal Obligation: unknown
- implement: true
- kind: ordinary

###### 3.13.2.2.6.2[2].[t]4.[r][5].[c][6] (Requirement Type)
- WordTraceId: 146135
- atomic: true
- Legal Obligation: unknown
- implement: true
- kind: ordinary

###### 3.13.2.2.6.2[2].[t]4.[r][6] (Requirement Type)
- WordTraceId: 146137
- atomic: false
- Legal Obligation: not applicable
- implement: false
- kind: Table

###### 3.13.2.2.6.2[2].[t]4.[r][6].[c][2] (Requirement Type)
T_brake_service
- WordTraceId: 146138
- atomic: true
- Legal Obligation: unknown
- implement: true
- kind: ordinary

###### 3.13.2.2.6.2[2].[t]4.[r][6].[c][3] (Requirement Type)
x
- WordTraceId: 146154
- atomic: true
- Legal Obligation: unknown
- implement: true
- kind: ordinary

###### 3.13.2.2.6.2[2].[t]4.[r][6].[c][4] (Requirement Type)
x
- WordTraceId: 146156
- atomic: true
- Legal Obligation: unknown
- implement: true
- kind: ordinary

###### 3.13.2.2.6.2[2].[t]4.[r][6].[c][5] (Requirement Type)
- WordTraceId: 146158
- atomic: true
- Legal Obligation: unknown
- implement: true
- kind: ordinary

###### 3.13.2.2.6.2[2].[t]4.[r][6].[c][6] (Requirement Type)
x
- WordTraceId: 146159
- atomic: true
- Legal Obligation: unknown
- implement: true
- kind: ordinary

###### 3.13.2.2.6.3 (Requirement Type)
When the brake percentage is captured as Train Data and the conversion model is applicable, A_brake_emergency(V), T_brake_emergency and A_brake_service(V) shall not be influenced by the status of a special brake. However, the conversion model offers the possibility that T_brake_service can be affected by the status of the regenerative brake, eddy current brake or Ep brake (see A.3.9).
- WordTraceId: 146263
- atomic: false
- Legal Obligation: mandatory
- implement: true
- implementerEnhanced: When
  [CONDITION]
  the brake percentage is captured as Train Data and the conversion model is applicable, A_brake_emergency(V), T_brake_emergency and A_brake_service(V) shall not be influenced by the status of a special brake. However, the conversion model offers the possibility that T_brake_service can be affected by the status of the regenerative brake, eddy current brake or Ep brake (see A.3.9).
- kind: ordinary
- CrossRefLink -> A.3.9

###### 3.13.2.2.6.4 (Requirement Type)
The on-board equipment shall be configured to define whether it is allowed to take into account the contribution of a special/additional brake, which is independent from wheel/rail adhesion, for the selection of the maximum emergency brake deceleration under reduced adhesion conditions (see 3.13.6.2.1.6).
- WordTraceId: 146651
- atomic: true
- Legal Obligation: mandatory
- implement: true
- implementerEnhanced: The
  on-board equipment
  [SELF]
  shall be configured to define
  whether
  [CONDITION]
  it is allowed to take into account the contribution of a special/additional brake, which is independent from wheel/rail adhesion, for the selection of the maximum emergency brake deceleration under reduced adhesion conditions (see 3.13.6.2.1.6).
- kind: ordinary
- CrossRefLink -> 3.13.6.2.1.6

###### 3.13.2.2.6.5 (Requirement Type)
Note: the choice to set to “allowed” the contribution of such special/additional brake in the selection of the maximum emergency braking effort, is rolling stock dependent.
- WordTraceId: 147003
- atomic: false
- Legal Obligation: not applicable
- implement: false
- kind: Note

###### 3.13.2.2.6.6 (Requirement Type)
If it is allowed to take into account the contribution of a special/additional brake, which is independent from wheel/rail adhesion, the speed and monitoring function shall take into account the status “active” or “not active” of the special/additional brake to select the appropriate National Value under reduced adhesion conditions (see 3.13.2.3.7.7).
- WordTraceId: 147176
- atomic: true
- Legal Obligation: mandatory
- implement: true
- implementerEnhanced: If
  [CONDITION]
  it is allowed to take into account the contribution of a special/additional brake, which is independent from wheel/rail adhesion, the speed and monitoring function shall take into account the status “active” or “not active” of the special/additional brake to select the appropriate National Value under reduced adhesion conditions (see 3.13.2.3.7.7).
- kind: ordinary
- CrossRefLink -> 3.13.2.3.7.7

###### 3.13.2.2.7 (Requirement Type)
Service brake interface
- WordTraceId: 147559
- atomic: false
- Legal Obligation: not applicable
- implement: false
- kind: Heading

###### 3.13.2.2.7.1 (Requirement Type)
The on-board shall be configured to define whether the service brake command is implemented or not, i.e. whether a service brake interface is implemented to command a full service brake effort.
- WordTraceId: 147583
- atomic: true
- Legal Obligation: mandatory
- implement: true
- implementerEnhanced: The on-board shall be configured to define
  whether
  [CONDITION]
  the service brake command is implemented or not, i.e.
  whether
  [CONDITION]
  a service brake interface is implemented to command a full service brake effort.
- kind: ordinary

###### 3.13.2.2.7.2 (Requirement Type)
The on-board shall be configured to define whether the service brake feedback is implemented or not, i.e. whether it is able to acquire from the service brake interface the information that the service brake is currently applied (e.g. from the main brake pipe pressure or brake cylinder pressure).
- WordTraceId: 147777
- atomic: true
- Legal Obligation: mandatory
- implement: true
- implementerEnhanced: The on-board shall be configured to define
  whether
  [CONDITION]
  the service brake feedback is implemented or not, i.e.
  whether
  [CONDITION]
  it is able to acquire from the service brake interface the information that the service brake is currently applied (
  e.g.
  [WEAK]
  from the main brake pipe pressure or brake cylinder pressure).
- kind: ordinary

###### 3.13.2.2.8 (Requirement Type)
Traction cut-off interface
- WordTraceId: 148075
- atomic: false
- Legal Obligation: not applicable
- implement: false
- kind: Heading

###### 3.13.2.2.8.1 (Requirement Type)
The on-board shall be configured to define whether the traction cut-off command is implemented, i.e. whether the interface to the traction system is implemented or not.
- WordTraceId: 148102
- atomic: true
- Legal Obligation: mandatory
- implement: true
- implementerEnhanced: The on-board shall be configured to define
  whether
  [CONDITION]
  the traction cut-off command is implemented, i.e.
  whether
  [CONDITION]
  the interface to the traction system is implemented or not.
- kind: ordinary

###### 3.13.2.2.9 (Requirement Type)
On-board Correction Factors
- WordTraceId: 148271
- atomic: false
- Legal Obligation: not applicable
- implement: false
- kind: Heading

###### 3.13.2.2.9.1 (Requirement Type)
Correction factors for the emergency deceleration
- WordTraceId: 148299
- atomic: false
- Legal Obligation: not applicable
- implement: false
- kind: Heading

###### 3.13.2.2.9.1.1 (Requirement Type)
If the braking models are captured as Train Data, rolling stock correction factors shall be defined in the ETCS on-board equipment. If the brake percentage is captured as Train Data and the conversion model is used (see 3.13.3.2 for its validity limits), no rolling stock correction factor shall apply.
- WordTraceId: 148349
- atomic: false
- Legal Obligation: mandatory
- implement: true
- implementerEnhanced: If
  [CONDITION]
  the braking models are captured as Train Data, rolling stock correction factors shall be defined in the ETCS
  on-board equipment
  [SELF]
  .
  If
  [CONDITION]
  the brake percentage is captured as Train Data and the conversion model is used (see 3.13.3.2 for its validity limits), no rolling stock correction factor shall apply.
- kind: ordinary
- CrossRefLink -> 3.13.3.2

###### 3.13.2.2.9.1.2 (Requirement Type)
For each defined individual speed dependent deceleration model of A_brake_emergency(V) (i.e. corresponding to each combination of use of regenerative brake, eddy current brake and magnetic shoe brake), one set of rolling stock correction factors Kdry_rst(V, EBCL) and Kwet_rst(V) shall be defined in the on-board equipment.
- WordTraceId: 148652
- atomic: true
- Legal Obligation: mandatory
- implement: true
- implementerEnhanced: For each
  [LOOP]
  defined individual speed dependent deceleration model of A_brake_emergency(V) (i.e. corresponding to each combination of use of regenerative brake, eddy current brake and magnetic shoe brake), one set of rolling stock correction factors Kdry_rst(V, EBCL) and Kwet_rst(V) shall be defined in the
  on-board equipment
  [SELF]
  .
- kind: ordinary

###### 3.13.2.2.9.1.3 (Requirement Type)
For a given confidence level on emergency brake safe deceleration (EBCL), the rolling stock correction factor Kdry_rst(V) shall be given as a step function of speed, with the same steps as the ones of A_brake_emergency(V).
- WordTraceId: 148976
- atomic: true
- Legal Obligation: mandatory
- implement: true
- kind: ordinary

###### 3.13.2.2.9.1.4 (Requirement Type)
The confidence level on emergency brake safe deceleration represents the probability of the following individual event: the rolling stock emergency brake subsystem of the train does ensure a deceleration at least equal to A_brake_emergency(V) * Kdry_rst(V), when the emergency brake is commanded on dry rails.
- WordTraceId: 149199
- atomic: true
- Legal Obligation: unknown
- implement: true
- implementerEnhanced: The confidence level on emergency brake safe deceleration represents the probability of the following individual event: the rolling stock emergency brake subsystem of the train does ensure a deceleration
  at least
  [WEAK]
  equal to A_brake_emergency(V) * Kdry_rst(V),
  when
  [CONDITION]
  the emergency brake is commanded on dry rails.
- kind: ordinary

###### 3.13.2.2.9.1.5 (Requirement Type)
The rolling stock correction factor Kwet_rst(V) shall be given as a step function of speed, with the same steps as the ones of A_brake_emergency(V). It represents the loss of deceleration with regards to emergency braking on dry rails, when the emergency brake is commanded on wet rails, according to wheel/rail adhesion reference conditions.
- WordTraceId: 149509
- atomic: false
- Legal Obligation: mandatory
- implement: true
- implementerEnhanced: The rolling stock correction factor Kwet_rst(V) shall be given as a step function of speed, with the same steps as the ones of A_brake_emergency(V). It represents the loss of deceleration with regards to emergency braking on dry rails,
  when
  [CONDITION]
  the emergency brake is commanded on wet rails, according to wheel/rail adhesion reference conditions.
- kind: ordinary

###### 3.13.2.2.9.2 (Requirement Type)
Correction factor for gradient on normal service deceleration
- WordTraceId: 149852
- atomic: false
- Legal Obligation: not applicable
- implement: false
- kind: Heading

###### 3.13.2.2.9.2.1 (Requirement Type)
The speed dependent correction factors for gradient on the normal service brake, Kn+(V) and Kn-(V), shall be given as step functions in the range from 0 to 10 m/s2.
- WordTraceId: 149914
- atomic: true
- Legal Obligation: mandatory
- implement: true
- kind: ordinary

###### 3.13.2.2.9.2.2 (Requirement Type)
It shall be possible to define up to five steps for Kn+(V) and for Kn-(V), respectively.
- WordTraceId: 150079
- atomic: true
- Legal Obligation: mandatory
- implement: true
- kind: ordinary

###### 3.13.2.2.9.2.3 (Requirement Type)
Note: An example with 4 steps is given in Figure 32. Kn is calculated as follows:
- WordTraceId: 150168
- atomic: false
- Legal Obligation: not applicable
- implement: false
- kind: Note
- CrossRefLink -> 3.13.2.2.9.2.3[2].[f]32.C

###### 3.13.2.2.9.2.3.*[1] (Requirement Type)
Kn = Kn_0 when 0 ≤ speed ≤ V1
- WordTraceId: 150276
- atomic: true
- Legal Obligation: unknown
- implement: false
- implementerEnhanced: Kn = Kn_0
  when
  [CONDITION]
  0 ≤ speed ≤ V1
- ListNumberText: ·
- kind: Note

###### 3.13.2.2.9.2.3.*[2] (Requirement Type)
Kn = Kn_1 when V1 < speed ≤ V2
- WordTraceId: 150306
- atomic: true
- Legal Obligation: unknown
- implement: false
- implementerEnhanced: Kn = Kn_1
  when
  [CONDITION]
  V1 < speed ≤ V2
- ListNumberText: ·
- kind: Note

###### 3.13.2.2.9.2.3.*[3] (Requirement Type)
Kn = Kn_2 when V2 < speed ≤ V3
- WordTraceId: 150337
- atomic: true
- Legal Obligation: unknown
- implement: false
- implementerEnhanced: Kn = Kn_2
  when
  [CONDITION]
  V2 < speed ≤ V3
- ListNumberText: ·
- kind: Note

###### 3.13.2.2.9.2.3.*[4] (Requirement Type)
Kn = Kn_3 when V3 < speed
- WordTraceId: 150368
- atomic: true
- Legal Obligation: unknown
- implement: false
- implementerEnhanced: Kn = Kn_3
  when
  [CONDITION]
  V3 < speed
- ListNumberText: ·
- kind: Note

###### 3.13.2.2.9.2.3[2] (Requirement Type)
- WordTraceId: 150394
- atomic: false
- Legal Obligation: not applicable
- implement: false
- kind: Placeholder

###### 3.13.2.2.9.2.3[2].[f]32 (Requirement Type)
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- WordTraceId: 150422
- atomic: false
- Legal Obligation: not applicable
- implement: false
- kind: Figure

###### 3.13.2.2.9.2.3[2].[f]32.C (Requirement Type)
Figure {Figure 32} Speed dependent correction factor for normal service brake (Kn)
- WordTraceId: 150422
- atomic: true
- Legal Obligation: unknown
- PlainText: Figure 32  Speed dependent correction factor for normal service brake (Kn)
- implement: false
- kind: Figure

###### 3.13.2.2.9.2.4 (Requirement Type)
Kn+(V) shall be applicable for positive gradients.
- WordTraceId: 150522
- atomic: true
- Legal Obligation: mandatory
- implement: true
- kind: ordinary

###### 3.13.2.2.9.2.5 (Requirement Type)
Kn-(V) shall be applicable for negative gradients.
- WordTraceId: 150573
- atomic: true
- Legal Obligation: mandatory
- implement: true
- kind: ordinary

###### 3.13.2.2.9.2.6 (Requirement Type)
The last step of the Kn+(V) or Kn-(V) shall by definition be considered as open ended, i.e. it has no upper speed limit.
- WordTraceId: 150624
- atomic: true
- Legal Obligation: mandatory
- implement: false
- kind: Definition

###### 3.13.2.2.10 (Requirement Type)
Nominal Rotating mass
- WordTraceId: 150745
- atomic: false
- Legal Obligation: not applicable
- implement: false
- kind: Heading

###### 3.13.2.2.10.1 (Requirement Type)
It shall be possible to define the nominal rotating mass to be used for compensating the gradient, instead of the two related fixed values defined in A3.1.
- WordTraceId: 150767
- atomic: true
- Legal Obligation: mandatory
- implement: true
- kind: ordinary
- CrossRefLink -> A.3.1

###### 3.13.2.2.11 (Requirement Type)
Train length
- WordTraceId: 150923
- atomic: false
- Legal Obligation: not applicable
- implement: false
- kind: Heading

###### 3.13.2.2.11.1 (Requirement Type)
The speed and distance monitoring shall take into account the train length acquired as part of Train Data (see section 3.18.3).
- WordTraceId: 150936
- atomic: true
- Legal Obligation: mandatory
- implement: true
- kind: ordinary
- CrossRefLink -> 3.18.3

###### 3.13.2.2.12 (Requirement Type)
Fixed values
- WordTraceId: 151064
- atomic: false
- Legal Obligation: not applicable
- implement: false
- kind: Heading

###### 3.13.2.2.12.1 (Requirement Type)
The speed and distance monitoring shall take into account the fixed values defined in A3.1 that are related to speed and distance monitoring.
- WordTraceId: 151077
- atomic: true
- Legal Obligation: mandatory
- implement: true
- kind: ordinary
- CrossRefLink -> A.3.1

###### 3.13.2.2.13 (Requirement Type)
Maximum train speed
- WordTraceId: 151219
- atomic: false
- Legal Obligation: not applicable
- implement: false
- kind: Heading

###### 3.13.2.2.13.1 (Requirement Type)
The speed and distance monitoring shall take into account the maximum train speed defined as part of Train Data (see section 3.18.3).
- WordTraceId: 151239
- atomic: true
- Legal Obligation: mandatory
- implement: true
- kind: ordinary
- CrossRefLink -> 3.18.3

##### 3.13.2.3 (Requirement Type)
Trackside related inputs
- WordTraceId: 151373
- atomic: false
- Legal Obligation: not applicable
- implement: false
- implementerEnhanced: Trackside
  [EXTERNAL]
  related inputs
- kind: Heading

###### 3.13.2.3.1 (Requirement Type)
Introduction
- WordTraceId: 151398
- atomic: false
- Legal Obligation: not applicable
- implement: false
- kind: Heading

###### 3.13.2.3.1.1 (Requirement Type)
The trackside related inputs to be considered for the speed and distance monitoring are:
- WordTraceId: 151411
- atomic: true
- Legal Obligation: unknown
- implement: false
- implementerEnhanced: The
  trackside
  [EXTERNAL]
  related inputs to be considered for the speed and distance monitoring are:
- kind: Heading

###### 3.13.2.3.1.1.a (Requirement Type)
Trackside related speed restrictions
- WordTraceId: 151500
- atomic: true
- Legal Obligation: unknown
- implement: true
- implementerEnhanced: Trackside
  [EXTERNAL]
  related speed restrictions
- ListNumberText: a)
- kind: ordinary

###### 3.13.2.3.1.1.b (Requirement Type)
Gradients
- WordTraceId: 151537
- atomic: true
- Legal Obligation: unknown
- implement: true
- ListNumberText: b)
- kind: ordinary

###### 3.13.2.3.1.1.c (Requirement Type)
Track conditions related to brake inhibition
- WordTraceId: 151547
- atomic: true
- Legal Obligation: unknown
- implement: true
- ListNumberText: c)
- kind: ordinary

###### 3.13.2.3.1.1.d (Requirement Type)
Track conditions related to powerless section
- WordTraceId: 151592
- atomic: true
- Legal Obligation: unknown
- implement: true
- ListNumberText: d)
- kind: ordinary

###### 3.13.2.3.1.1.e (Requirement Type)
Reduced adhesion conditions
- WordTraceId: 151638
- atomic: true
- Legal Obligation: unknown
- implement: true
- ListNumberText: e)
- kind: ordinary

###### 3.13.2.3.1.1.f (Requirement Type)
Specific speed and distance limits (e.g. EOA/SvL)
- WordTraceId: 151666
- atomic: false
- Legal Obligation: unknown
- implement: true
- implementerEnhanced: Specific speed and distance limits (
  e.g.
  [WEAK]
  EOA/SvL)
- ListNumberText: f)
- kind: ordinary

###### 3.13.2.3.1.1.g (Requirement Type)
National Values
- WordTraceId: 151716
- atomic: true
- Legal Obligation: unknown
- implement: true
- ListNumberText: g)
- kind: ordinary

###### 3.13.2.3.2 (Requirement Type)
Trackside related speed restrictions
- WordTraceId: 151732
- atomic: false
- Legal Obligation: not applicable
- implement: false
- implementerEnhanced: Trackside
  [EXTERNAL]
  related speed restrictions
- kind: Heading

###### 3.13.2.3.2.1 (Requirement Type)
The speed and distance monitoring shall take into account the trackside related speed restrictions composed of all speed restrictions mentioned in 3.11.2 except the maximum train speed.
- WordTraceId: 151769
- atomic: true
- Legal Obligation: mandatory
- implement: true
- implementerEnhanced: The speed and distance monitoring shall take into account the
  trackside
  [EXTERNAL]
  related speed restrictions composed of all speed restrictions mentioned in 3.11.2 except the maximum train speed.
- kind: ordinary
- CrossRefLink -> 3.11.2

###### 3.13.2.3.3 (Requirement Type)
Gradients
- WordTraceId: 151955
- atomic: false
- Legal Obligation: not applicable
- implement: false
- kind: Heading

###### 3.13.2.3.3.1 (Requirement Type)
The speed and distance monitoring shall take into account the gradient profile and the default gradient for TSR (see section 3.11.12).
- WordTraceId: 151965
- atomic: true
- Legal Obligation: mandatory
- implement: true
- kind: ordinary
- CrossRefLink -> 3.11.12

###### 3.13.2.3.4 (Requirement Type)
Track conditions
- WordTraceId: 152129
- atomic: false
- Legal Obligation: not applicable
- implement: false
- kind: Heading

###### 3.13.2.3.4.1 (Requirement Type)
The speed and distance monitoring shall take into account the following types of track condition received from trackside (see section 3.12.1): powerless section, inhibition of regenerative brake, eddy current brake and magnetic shoe brake.
- WordTraceId: 152146
- atomic: true
- Legal Obligation: mandatory
- implement: true
- implementerEnhanced: The speed and distance monitoring shall take into account the following types of track condition received from
  trackside
  [EXTERNAL]
  (see section 3.12.1): powerless section, inhibition of regenerative brake, eddy current brake and magnetic shoe brake.
- kind: ordinary
- CrossRefLink -> 3.12.1

###### 3.13.2.3.5 (Requirement Type)
Reduced adhesion conditions
- WordTraceId: 152386
- atomic: false
- Legal Obligation: not applicable
- implement: false
- kind: Heading

###### 3.13.2.3.5.1 (Requirement Type)
The speed and distance monitoring shall take into account the track reduced adhesion received from trackside or selected by the driver (see section 3.18.4.6).
- WordTraceId: 152414
- atomic: true
- Legal Obligation: mandatory
- implement: true
- implementerEnhanced: The speed and distance monitoring shall take into account the track reduced adhesion received from
  trackside
  [EXTERNAL]
  or selected by the
  driver
  [EXTERNAL]
  (see section 3.18.4.6).
- kind: ordinary
- CrossRefLink -> 3.18.4.6

###### 3.13.2.3.6 (Requirement Type)
Specific speed / distance limits
- WordTraceId: 152573
- atomic: false
- Legal Obligation: not applicable
- implement: false
- kind: Heading

###### 3.13.2.3.6.1 (Requirement Type)
The speed and distance monitoring shall take into account the following limits:
- WordTraceId: 152606
- atomic: true
- Legal Obligation: mandatory
- implement: true
- kind: ordinary

###### 3.13.2.3.6.1.a (Requirement Type)
the Limit of Authority (LOA), the End of Authority (EOA), the Supervised Location (SvL) and its associated release speed, if any.
- WordTraceId: 152686
- atomic: true
- Legal Obligation: mandatory
- implement: true
- implementerEnhanced: the Limit of Authority (LOA), the End of Authority (EOA), the Supervised Location (SvL) and its associated release speed,
  if
  [CONDITION]
  any.
- ListNumberText: a)
- kind: ordinary

###### 3.13.2.3.6.1.b (Requirement Type)
the maximum permitted distance to run in Staff Responsible
- WordTraceId: 152816
- atomic: true
- Legal Obligation: mandatory
- implement: true
- ListNumberText: b)
- kind: ordinary

###### 3.13.2.3.7 (Requirement Type)
National Values for speed and distance monitoring
- WordTraceId: 152875
- atomic: false
- Legal Obligation: not applicable
- implement: false
- kind: Heading

###### 3.13.2.3.7.1 (Requirement Type)
It shall be possible by means of a National Value to inhibit the use of the service brake command in target speed monitoring.
- WordTraceId: 152925
- atomic: true
- Legal Obligation: mandatory
- implement: true
- kind: ordinary

###### 3.13.2.3.7.2 (Requirement Type)
It shall be possible to state by means of a National Value whether an emergency brake command has to be revoked, both in ceiling speed and target speed monitoring, when:
- WordTraceId: 153051
- atomic: true
- Legal Obligation: mandatory
- implement: true
- implementerEnhanced: It shall be possible to state by means of a National Value
  whether
  [CONDITION]
  an emergency brake command has to be revoked, both in ceiling speed and target speed monitoring,
  when
  [CONDITION]
  :
- kind: ordinary

###### 3.13.2.3.7.2.a (Requirement Type)
the Permitted Speed supervision limit is no longer exceeded, or
- WordTraceId: 153221
- atomic: true
- Legal Obligation: mandatory (>= 1)
- implement: true
- ListNumberText: a)
- kind: ordinary

###### 3.13.2.3.7.2.b (Requirement Type)
the train is at standstill.
- WordTraceId: 153285
- atomic: true
- Legal Obligation: mandatory (>= 1)
- implement: true
- ListNumberText: b)
- kind: ordinary

###### 3.13.2.3.7.3 (Requirement Type)
It shall be possible by means of a National Value to inhibit the guidance curve (GUI).
- WordTraceId: 153313
- atomic: true
- Legal Obligation: mandatory
- implement: true
- kind: ordinary

###### 3.13.2.3.7.4 (Requirement Type)
It shall be possible by means of a National Value to inhibit the service brake feedback function.
- WordTraceId: 153400
- atomic: true
- Legal Obligation: mandatory
- implement: true
- kind: ordinary

###### 3.13.2.3.7.5 (Requirement Type)
It shall be possible by means of National Values to indicate to the on-board equipment the required confidence level on the emergency brake safe deceleration, when the emergency brake is commanded on dry rails (see 3.13.2.2.9.1.4).
- WordTraceId: 153498
- atomic: true
- Legal Obligation: mandatory
- implement: true
- implementerEnhanced: It shall be possible by means of National Values to indicate to the
  on-board equipment
  [SELF]
  the required confidence level on the emergency brake safe deceleration,
  when
  [CONDITION]
  the emergency brake is commanded on dry rails (see 3.13.2.2.9.1.4).
- kind: ordinary
- CrossRefLink -> 3.13.2.2.9.1.4

###### 3.13.2.3.7.6 (Requirement Type)
It shall be possible by means of a National Value to indicate to the on-board equipment the available wheel/rail adhesion, weighted between the wheel/rail adhesion for dry rails and the wheel/rail adhesion for wet rails according to reference conditions.
- WordTraceId: 153730
- atomic: true
- Legal Obligation: mandatory
- implement: true
- implementerEnhanced: It shall be possible by means of a National Value to indicate to the
  on-board equipment
  [SELF]
  the available wheel/rail adhesion, weighted between the wheel/rail adhesion for dry rails and the wheel/rail adhesion for wet rails according to reference conditions.
- kind: ordinary

###### 3.13.2.3.7.7 (Requirement Type)
In order to adapt the train behaviour under reduced adhesion conditions, it shall be possible by means of National Values to limit to a maximum value the speed dependent deceleration for the emergency brake. Three values shall be applicable for a given combination of the brake position and of the type of brakes:
- WordTraceId: 153985
- atomic: false
- Legal Obligation: mandatory
- implement: true
- kind: ordinary

###### 3.13.2.3.7.7.a (Requirement Type)
the first value shall be used for “Passenger train in P” with special/additional brakes independent from wheel/rail adhesion;
- WordTraceId: 154299
- atomic: true
- Legal Obligation: mandatory
- implement: true
- implementerEnhanced: the first value shall be used for “
  Passenger train in P
  [LINKED_PHRASE]
  ” with special/additional brakes independent from wheel/rail adhesion;
- ListNumberText: a)
- kind: ordinary
- KnownTermLink -> 3.13.2.2.3.1.9.b

###### 3.13.2.3.7.7.b (Requirement Type)
the second value shall be used for “Passenger train in P” without special/additional brakes independent from wheel/rail adhesion;
- WordTraceId: 154425
- atomic: true
- Legal Obligation: mandatory
- implement: true
- implementerEnhanced: the second value shall be used for “
  Passenger train in P
  [LINKED_PHRASE]
  ” without special/additional brakes independent from wheel/rail adhesion;
- ListNumberText: b)
- kind: ordinary
- KnownTermLink -> 3.13.2.2.3.1.9.b

###### 3.13.2.3.7.7.c (Requirement Type)
the third value shall be used for “Freight train in P” or “Freight train in G”.
- WordTraceId: 154555
- atomic: true
- Legal Obligation: mandatory
- implement: true
- implementerEnhanced: the third value shall be used for “
  Freight train in P
  [LINKED_PHRASE]
  ” or “
  Freight train in G
  [LINKED_PHRASE]
  ”.
- ListNumberText: c)
- kind: ordinary
- KnownTermLink -> 3.13.2.2.3.1.9.a
- KnownTermLink -> 3.13.2.2.3.1.9.b

###### 3.13.2.3.7.8 (Requirement Type)
It shall be possible by means of a National Value to specify a release speed.
- WordTraceId: 154635
- atomic: true
- Legal Obligation: mandatory
- implement: true
- kind: ordinary

###### 3.13.2.3.7.9 (Requirement Type)
It shall be possible by means of a National Value to inhibit the compensation of the speed measurement inaccuracy.
- WordTraceId: 154713
- atomic: true
- Legal Obligation: mandatory
- implement: true
- kind: ordinary

###### 3.13.2.3.7.10 (Requirement Type)
It shall be possible by means of National Values to define integrated correction factors, namely Kv_int(V), Kr_int(l) and Kt_int. The integrated correction factors only apply to the on-board equipment when the conversion model is used.
- WordTraceId: 154828
- atomic: false
- Legal Obligation: mandatory
- implement: true
- implementerEnhanced: It shall be possible by means of National Values to define integrated correction factors, namely Kv_int(V), Kr_int(l) and Kt_int. The integrated correction factors only apply to the
  on-board equipment
  [SELF]
  when
  [CONDITION]
  the conversion model is used.
- kind: ordinary

###### 3.13.2.3.7.11 (Requirement Type)
The speed dependent correction factor, Kv_int(V), shall be given as a step function.
- WordTraceId: 155064
- atomic: true
- Legal Obligation: mandatory
- implement: true
- kind: ordinary

###### 3.13.2.3.7.11.1 (Requirement Type)
It shall be possible to define up to five steps for Kv_int(V).
- WordTraceId: 155149
- atomic: true
- Legal Obligation: mandatory
- implement: true
- kind: ordinary

###### 3.13.2.3.7.11.2 (Requirement Type)
Note: An example with 4 steps is given in Figure 33. Kv_int is calculated as follows:
- WordTraceId: 155212
- atomic: false
- Legal Obligation: not applicable
- implement: false
- kind: Note
- CrossRefLink -> 3.13.2.3.7.11.2[2].[f]33.C

###### 3.13.2.3.7.11.2.*[1] (Requirement Type)
Kv_int = Kv_int_0 when 0 ≤ speed ≤ V1
- WordTraceId: 155324
- atomic: true
- Legal Obligation: unknown
- implement: false
- implementerEnhanced: Kv_int = Kv_int_0
  when
  [CONDITION]
  0 ≤ speed ≤ V1
- ListNumberText: ·
- kind: Note

###### 3.13.2.3.7.11.2.*[2] (Requirement Type)
Kv_int = Kv_int_1 when V1 < speed ≤ V2
- WordTraceId: 155362
- atomic: true
- Legal Obligation: unknown
- implement: false
- implementerEnhanced: Kv_int = Kv_int_1
  when
  [CONDITION]
  V1 < speed ≤ V2
- ListNumberText: ·
- kind: Note

###### 3.13.2.3.7.11.2.*[3] (Requirement Type)
Kv_int = Kv_int_2 when V2 < speed ≤ V3
- WordTraceId: 155401
- atomic: true
- Legal Obligation: unknown
- implement: false
- implementerEnhanced: Kv_int = Kv_int_2
  when
  [CONDITION]
  V2 < speed ≤ V3
- ListNumberText: ·
- kind: Note

###### 3.13.2.3.7.11.2.*[4] (Requirement Type)
Kv_int = Kv_int_3 when V3 < speed
- WordTraceId: 155440
- atomic: true
- Legal Obligation: unknown
- implement: false
- implementerEnhanced: Kv_int = Kv_int_3
  when
  [CONDITION]
  V3 < speed
- ListNumberText: ·
- kind: Note

###### 3.13.2.3.7.11.2[2] (Requirement Type)
- WordTraceId: 155474
- atomic: false
- Legal Obligation: not applicable
- implement: false
- kind: Placeholder

###### 3.13.2.3.7.11.2[2].[f]33 (Requirement Type)
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- WordTraceId: 155502
- atomic: false
- Legal Obligation: not applicable
- implement: false
- kind: Figure

###### 3.13.2.3.7.11.2[2].[f]33.C (Requirement Type)
Figure {Figure 33} Speed dependent correction factor Kv_int
- WordTraceId: 155502
- atomic: true
- Legal Obligation: unknown
- PlainText: Figure 33  Speed dependent correction factor Kv_int
- implement: false
- kind: Figure

###### 3.13.2.3.7.11.3 (Requirement Type)
It shall be possible to define up to 2 sets of Kv_int with separate speed limits V1, V2, .. for each set. The sets of Kv_int relate to the following train types:
- WordTraceId: 155579
- atomic: false
- Legal Obligation: mandatory
- implement: true
- implementerEnhanced: It shall be possible to define up to 2 sets of Kv_int with separate speed limits V1, V2, ..
  for each
  [LOOP]
  set. The sets of Kv_int relate to the following train types:
- kind: ordinary

###### 3.13.2.3.7.11.3[2] (Requirement Type)
1) Freight trains
2) Conventional passenger trains
- WordTraceId: 155741
- atomic: true
- Legal Obligation: unknown
- implement: true
- kind: ordinary

###### 3.13.2.3.7.11.3[2].1 (Requirement Type)
Note: Different sets of Kv_int are needed for different types of trains in order to compensate the absence of the rolling stock related correction factors when the conversion model is used.
- WordTraceId: 155794
- atomic: false
- Legal Obligation: not applicable
- implement: false
- implementerEnhanced: Note: Different sets of Kv_int are needed for different types of trains in order to compensate the absence of the rolling stock related correction factors
  when
  [CONDITION]
  the conversion model is used.
- ListNumberText: 3.13.2.3.7.11.3.1
- kind: Note

###### 3.13.2.3.7.11.4 (Requirement Type)
The set of Kv_int for conventional passenger trains shall be divided into two sub sets Kv_int_x_a and Kv_int_x_b, with identical speed limits V1, V2, ....
- WordTraceId: 155984
- atomic: true
- Legal Obligation: mandatory
- implement: true
- implementerEnhanced: The set of Kv_int for conventional passenger trains shall be divided into two sub sets Kv_int_x_a and Kv_int_x_b, with identical speed limits V1, V2,
  ...
  [WEAK]
  .
- kind: ordinary

###### 3.13.2.3.7.11.5 (Requirement Type)
Subset Kv_int_x_a shall be applicable for maximum emergency brake deceleration lower or equal to a deceleration limit, defined as a National Value.
- WordTraceId: 156139
- atomic: true
- Legal Obligation: mandatory
- implement: true
- kind: ordinary

###### 3.13.2.3.7.11.6 (Requirement Type)
Subset Kv_int_x_b shall be applicable for maximum emergency brake deceleration greater or equal to a deceleration limit, defined as a National Value.
- WordTraceId: 156287
- atomic: true
- Legal Obligation: mandatory
- implement: true
- kind: ordinary

###### 3.13.2.3.7.12 (Requirement Type)
The train length dependent correction factor, Kr_int(l), shall be given as a step function.
- WordTraceId: 156437
- atomic: true
- Legal Obligation: mandatory
- implement: true
- kind: ordinary

###### 3.13.2.3.7.12.1 (Requirement Type)
It shall be possible to define up to five steps for Kr_int(l).
- WordTraceId: 156529
- atomic: true
- Legal Obligation: mandatory
- implement: true
- kind: ordinary

###### 3.13.2.3.7.12.2 (Requirement Type)
Note: An example with 4 steps is given in Figure 34. Kr_int is calculated as follows:
- WordTraceId: 156592
- atomic: false
- Legal Obligation: not applicable
- implement: false
- kind: Note
- CrossRefLink -> 3.13.2.3.7.12.2[2].[f]34.C

###### 3.13.2.3.7.12.2.*[1] (Requirement Type)
Kr_int = Kr_int_0 when 0 ≤ train length ≤ L1
- WordTraceId: 156704
- atomic: true
- Legal Obligation: unknown
- implement: false
- implementerEnhanced: Kr_int = Kr_int_0
  when
  [CONDITION]
  0 ≤ train length ≤ L1
- ListNumberText: ·
- kind: Note

###### 3.13.2.3.7.12.2.*[2] (Requirement Type)
Kr_int = Kr_int_1 when L1 < train length ≤ L2
- WordTraceId: 156749
- atomic: true
- Legal Obligation: unknown
- implement: false
- implementerEnhanced: Kr_int = Kr_int_1
  when
  [CONDITION]
  L1 < train length ≤ L2
- ListNumberText: ·
- kind: Note

###### 3.13.2.3.7.12.2.*[3] (Requirement Type)
Kr_int = Kr_int_2 when L2 < train length ≤ L3
- WordTraceId: 156795
- atomic: true
- Legal Obligation: unknown
- implement: false
- implementerEnhanced: Kr_int = Kr_int_2
  when
  [CONDITION]
  L2 < train length ≤ L3
- ListNumberText: ·
- kind: Note

###### 3.13.2.3.7.12.2.*[4] (Requirement Type)
Kr_int = Kr_int_3 when L3 < train length
- WordTraceId: 156841
- atomic: true
- Legal Obligation: unknown
- implement: false
- implementerEnhanced: Kr_int = Kr_int_3
  when
  [CONDITION]
  L3 < train length
- ListNumberText: ·
- kind: Note

###### 3.13.2.3.7.12.2[2] (Requirement Type)
- WordTraceId: 156883
- atomic: false
- Legal Obligation: not applicable
- implement: false
- kind: Placeholder

###### 3.13.2.3.7.12.2[2].[f]34 (Requirement Type)
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- WordTraceId: 156911
- atomic: false
- Legal Obligation: not applicable
- implement: false
- kind: Figure

###### 3.13.2.3.7.12.2[2].[f]34.C (Requirement Type)
Figure {Figure 34} Train length dependent correction factor Kr_int
- WordTraceId: 156911
- atomic: true
- Legal Obligation: unknown
- PlainText: Figure 34  Train length dependent correction factor Kr_int
- implement: false
- kind: Figure

###### 3.13.2.3.7.13 (Requirement Type)
The last step of the Kv_int(V) and Kr_int(l) shall by definition be considered as open ended, i.e. it has no upper speed and train length limit, respectively.
- WordTraceId: 156995
- atomic: true
- Legal Obligation: mandatory
- implement: false
- kind: Definition

###### 3.13.2.3.7.14 (Requirement Type)
The correction factor for brake build up time (Kt_int) shall be a single parameter.
- WordTraceId: 157154
- atomic: true
- Legal Obligation: mandatory
- implement: true
- implementerEnhanced: The correction factor for brake build up
  time
  [TIME]
  (Kt_int) shall be a single parameter.
- kind: ordinary

#### 3.13.3 (Requirement Type)
Conversion Models
- WordTraceId: 157238
- atomic: false
- Legal Obligation: not applicable
- implement: false
- kind: Heading

##### 3.13.3.1 (Requirement Type)
Introduction
- WordTraceId: 157256
- atomic: false
- Legal Obligation: not applicable
- implement: false
- kind: Heading

###### 3.13.3.1.1 (Requirement Type)
For trains with variable composition (loco hauled trains), the brake characteristics can vary together with the composition of the train. In this case, it is not convenient to pre-program the brake parameters necessary to calculate the braking curves. The only practical way to obtain the correct values for the current train composition is to include them into the data entry process by the driver. However, it cannot be expected from the driver to know deceleration values and brake build up times. Conversion models are therefore defined to convert the parameters entered by the driver (brake percentage and brake position) into the parameters of the corresponding brake model.
- WordTraceId: 157269
- atomic: false
- Legal Obligation: unknown
- implement: true
- implementerEnhanced: For trains with variable composition (loco hauled trains), the brake characteristics can vary together with the composition of the train. In this case, it is not convenient to pre-program the brake parameters necessary to calculate the braking curves. The only practical way to obtain the correct values for the current train composition is to include them into the data entry process by the
  driver
  [EXTERNAL]
  . However, it cannot be expected from the
  driver
  [EXTERNAL]
  to know deceleration values and brake build up times. Conversion models are therefore defined to convert the parameters entered by the
  driver
  [EXTERNAL]
  (brake percentage and brake position) into the parameters of the corresponding brake model.
- kind: ordinary

###### 3.13.3.1.2 (Requirement Type)
Note: The process for defining the input parameters for the conversion model (brake percentage and brake position) is outside the scope of the ERTMS/ETCS specifications.
- WordTraceId: 157950
- atomic: false
- Legal Obligation: not applicable
- implement: false
- kind: Note

##### 3.13.3.2 (Requirement Type)
Applicability of the conversion models
- WordTraceId: 158120
- atomic: false
- Legal Obligation: not applicable
- implement: false
- kind: Heading

###### 3.13.3.2.a (Requirement Type)
The conversion models shall be used by the on-board equipment if the brake percentage is acquired as part of Train Data, and if the maximum train speed, the brake percentage and the train length are all within the following validity limits of the conversion models:
- WordTraceId: 158159
- atomic: true
- Legal Obligation: mandatory
- implement: true
- implementerEnhanced: The conversion models shall be used by the
  on-board equipment
  [SELF]
  if
  [CONDITION]
  the brake percentage is acquired as part of Train Data, and
  if
  [CONDITION]
  the maximum train speed, the brake percentage and the train length are all within the following validity limits of the conversion models:
- ListNumberText: a)
- kind: ordinary

###### 3.13.3.2.b (Requirement Type)
0 ≤ V ≤ 200, where V is the maximum train speed in km/h
- WordTraceId: 158425
- atomic: true
- Legal Obligation: unknown
- implement: true
- ListNumberText: b)
- kind: ordinary

###### 3.13.3.2.c (Requirement Type)
30 ≤ λ ≤ 250, where λ is the brake percentage in %
- WordTraceId: 158481
- atomic: true
- Legal Obligation: unknown
- implement: true
- ListNumberText: c)
- kind: ordinary

###### 3.13.3.2.d (Requirement Type)
0 ≤ L ≤ Lmax, where L is the train length in m and where Lmax = 900 m if the brake position is “Passenger train in P” or Lmax = 1500 m if the brake position is “Freight train in P” or “Freight train in G”
- WordTraceId: 158532
- atomic: true
- Legal Obligation: unknown
- implement: true
- implementerEnhanced: 0 ≤ L ≤ Lmax, where L is the train length in m and where Lmax = 900 m
  if
  [CONDITION]
  the brake position is “
  Passenger train in P
  [LINKED_PHRASE]
  ” or Lmax = 1500 m
  if
  [CONDITION]
  the brake position is “
  Freight train in P
  [LINKED_PHRASE]
  ” or “
  Freight train in G
  [LINKED_PHRASE]
  ”
- ListNumberText: d)
- kind: ordinary
- KnownTermLink -> 3.13.2.2.3.1.9.b
- KnownTermLink -> 3.13.2.2.3.1.9.a

###### 3.13.3.2.1 (Requirement Type)
PLACEHOLDER REQUIREMENT - DO NOT TRACE
- WordTraceId: 158737
- atomic: false
- Legal Obligation: not applicable
- implement: false
- kind: Placeholder

###### 3.13.3.2.1.1 (Requirement Type)
Note: The overspeed above the maximum train speed which may occur due to the ceiling speed margins is taken into account in the definition of the conversion model.
- WordTraceId: 158737
- atomic: false
- Legal Obligation: optional
- implement: false
- implementerEnhanced: Note: The overspeed
  above
  [WEAK]
  the maximum train speed which may occur due to the ceiling speed margins is taken into account in the definition of the conversion model.
- kind: Note

###### 3.13.3.2.2 (Requirement Type)
For trains not fitting into at least one of those validity limits, it is still possible to acquire the brake percentage as Train Data, but the conversion models are not applicable, which means that braking models (i.e. pre-programmed deceleration profiles and brake build up times) shall be used by the speed and distance monitoring function.
- WordTraceId: 158901
- atomic: true
- Legal Obligation: mandatory
- implement: true
- implementerEnhanced: For trains not fitting into
  at least
  [WEAK]
  one of those validity limits, it is still possible to acquire the brake percentage as Train Data, but the conversion models are not applicable, which means that braking models (i.e. pre-programmed deceleration profiles and brake build up times) shall be used by the speed and distance monitoring function.
- kind: ordinary

##### 3.13.3.3 (Requirement Type)
Brake percentage conversion model
- WordTraceId: 159244
- atomic: false
- Legal Obligation: not applicable
- implement: false
- kind: Heading

###### 3.13.3.3.1 (Requirement Type)
Input parameters
- WordTraceId: 159278
- atomic: false
- Legal Obligation: not applicable
- implement: false
- kind: Heading

###### 3.13.3.3.1.1 (Requirement Type)
The input for the model shall be the brake percentage of the train as defined in 3.13.2.2.5.
- WordTraceId: 159295
- atomic: true
- Legal Obligation: mandatory
- implement: true
- kind: ordinary
- CrossRefLink -> 3.13.2.2.5

###### 3.13.3.3.2 (Requirement Type)
Calculation of the basic deceleration
- WordTraceId: 159417
- atomic: false
- Legal Obligation: not applicable
- implement: false
- kind: Heading

###### 3.13.3.3.2.1 (Requirement Type)
The basic deceleration A_basic(V) shall be given as a step function of the speed using the algorithm defined in Appendix A3.7.
- WordTraceId: 159455
- atomic: true
- Legal Obligation: mandatory
- implement: true
- kind: ordinary
- CrossRefLink -> A.3.7

###### 3.13.3.3.3 (Requirement Type)
Output parameters
- WordTraceId: 159582
- atomic: false
- Legal Obligation: not applicable
- implement: false
- kind: Heading

###### 3.13.3.3.3.1 (Requirement Type)
The output of the brake percentage conversion model shall consist of two speed dependent deceleration brake models, A_brake_emergency(V) for the emergency brake and A_brake_service(V) for the service brake.
- WordTraceId: 159600
- atomic: true
- Legal Obligation: mandatory
- implement: true
- kind: ordinary

##### 3.13.3.4 (Requirement Type)
Brake position conversion model
- WordTraceId: 159807
- atomic: false
- Legal Obligation: not applicable
- implement: false
- kind: Heading

###### 3.13.3.4.1 (Requirement Type)
Input parameters
- WordTraceId: 159839
- atomic: false
- Legal Obligation: not applicable
- implement: false
- kind: Heading

###### 3.13.3.4.1.1 (Requirement Type)
The input for the model shall consist of the brake position of the train as defined in 3.13.2.2.4, the train length and the target speed.
- WordTraceId: 159856
- atomic: true
- Legal Obligation: mandatory
- implement: true
- kind: ordinary
- CrossRefLink -> 3.13.2.2.4

###### 3.13.3.4.2 (Requirement Type)
Calculation of the emergency brake equivalent time
- WordTraceId: 160023
- atomic: false
- Legal Obligation: not applicable
- implement: false
- implementerEnhanced: Calculation of the emergency brake equivalent
  time
  [TIME]
- kind: Heading

###### 3.13.3.4.2.1 (Requirement Type)
The equivalent brake build up time for the emergency brake shall be determined as specified in Appendix A3.8.
- WordTraceId: 160074
- atomic: true
- Legal Obligation: mandatory
- implement: true
- implementerEnhanced: The equivalent brake build up
  time
  [TIME]
  for the emergency brake shall be determined as specified in Appendix A3.8.
- kind: ordinary
- CrossRefLink -> A.3.8

###### 3.13.3.4.3 (Requirement Type)
Calculation of the full service brake equivalent time
- WordTraceId: 160184
- atomic: false
- Legal Obligation: not applicable
- implement: false
- implementerEnhanced: Calculation of the full service brake equivalent
  time
  [TIME]
- kind: Heading

###### 3.13.3.4.3.1 (Requirement Type)
The equivalent brake build up time for the full service brake shall be determined as specified in Appendix A3.9.
- WordTraceId: 160238
- atomic: true
- Legal Obligation: mandatory
- implement: true
- implementerEnhanced: The equivalent brake build up
  time
  [TIME]
  for the full service brake shall be determined as specified in Appendix A3.9.
- kind: ordinary
- CrossRefLink -> A.3.9

###### 3.13.3.4.4 (Requirement Type)
Output parameters
- WordTraceId: 160351
- atomic: false
- Legal Obligation: not applicable
- implement: false
- kind: Heading

###### 3.13.3.4.4.1 (Requirement Type)
The outputs of the brake position conversion model shall consist of:
- WordTraceId: 160369
- atomic: true
- Legal Obligation: mandatory
- implement: true
- kind: ordinary

###### 3.13.3.4.4.1.a (Requirement Type)
two values of the equivalent brake build up time to be used when the target speed (V_target) is equal to zero, one value for the emergency brake and one for the full service brake:
- WordTraceId: 160438
- atomic: true
- Legal Obligation: unknown
- implement: true
- implementerEnhanced: two values of the equivalent brake build up
  time
  [TIME]
  to be used
  when
  [CONDITION]
  the target speed (V_target) is equal to zero, one value for the emergency brake and one for the full service brake:
- ListNumberText: a)
- kind: ordinary

###### 3.13.3.4.4.1.a[2] (Requirement Type)
T_brake_emergency_cm0 as defined for emergency brake in A3.8
- WordTraceId: 160619
- atomic: true
- Legal Obligation: unknown
- implement: true
- kind: ordinary
- CrossRefLink -> A.3.8

###### 3.13.3.4.4.1.a[3] (Requirement Type)
T_brake_service_cm0 as defined for service brake in A3.9
- WordTraceId: 160680
- atomic: true
- Legal Obligation: unknown
- implement: true
- kind: ordinary
- CrossRefLink -> A.3.9

###### 3.13.3.4.4.1.b (Requirement Type)
two values of the equivalent brake build up time to be used when the target speed (V_target) is different from zero, one value for the emergency brake and one for the full service brake:
- WordTraceId: 160737
- atomic: true
- Legal Obligation: unknown
- implement: true
- implementerEnhanced: two values of the equivalent brake build up
  time
  [TIME]
  to be used
  when
  [CONDITION]
  the target speed (V_target) is different from zero, one value for the emergency brake and one for the full service brake:
- ListNumberText: b)
- kind: ordinary

###### 3.13.3.4.4.1.b[2] (Requirement Type)
T_brake_emergency_cmt as defined for emergency brake in A3.8
- WordTraceId: 160924
- atomic: true
- Legal Obligation: unknown
- implement: true
- kind: ordinary
- CrossRefLink -> A.3.8

###### 3.13.3.4.4.1.b[3] (Requirement Type)
T_brake_service_cmt as defined for service brake in A3.9
- WordTraceId: 160985
- atomic: true
- Legal Obligation: unknown
- implement: true
- kind: ordinary
- CrossRefLink -> A.3.9

#### 3.13.4 (Requirement Type)
Acceleration / Deceleration due to gradient
- WordTraceId: 161042
- atomic: false
- Legal Obligation: not applicable
- implement: false
- kind: Heading

##### 3.13.4.1 (Requirement Type)
Introduction
- WordTraceId: 161086
- atomic: false
- Legal Obligation: not applicable
- implement: false
- kind: Heading

###### 3.13.4.1.1 (Requirement Type)
The elements of the gradient profile given from trackside shall be compensated:
- WordTraceId: 161099
- atomic: true
- Legal Obligation: mandatory
- implement: true
- implementerEnhanced: The elements of the gradient profile given from
  trackside
  [EXTERNAL]
  shall be compensated:
- kind: ordinary

###### 3.13.4.1.1.a (Requirement Type)
in location according to the train length as defined in 3.13.4.2
- WordTraceId: 161179
- atomic: true
- Legal Obligation: unknown
- implement: true
- ListNumberText: a)
- kind: ordinary
- CrossRefLink -> 3.13.4.2

###### 3.13.4.1.1.b (Requirement Type)
in value according to the rotating mass as defined in 3.13.4.3 in order to derive the corresponding acceleration/deceleration.
- WordTraceId: 161289
- atomic: true
- Legal Obligation: unknown
- implement: true
- ListNumberText: b)
- kind: ordinary
- CrossRefLink -> 3.13.4.3

###### 3.13.4.1.1[2] (Requirement Type)
- WordTraceId: 161461
- atomic: false
- Legal Obligation: not applicable
- implement: false
- kind: Placeholder

###### 3.13.4.1.1[2].[f]35 (Requirement Type)
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- WordTraceId: 161489
- atomic: false
- Legal Obligation: not applicable
- implement: false
- kind: Figure

###### 3.13.4.1.1[2].[f]35.C (Requirement Type)
Figure {Figure 35}: Compensation on the gradient profile
- WordTraceId: 161489
- atomic: true
- Legal Obligation: unknown
- PlainText: Figure 35: Compensation on the gradient profile
- implement: false
- kind: Figure

###### 3.13.4.1.2 (Requirement Type)
The default gradient for TSR shall be compensated in value according to the rotating mass as defined in 3.13.4.3.
- WordTraceId: 161562
- atomic: true
- Legal Obligation: mandatory
- implement: true
- kind: ordinary
- CrossRefLink -> 3.13.4.3

###### 3.13.4.1.3 (Requirement Type)
For all locations not covered by the gradient profile, the on-board shall consider the gradient value as:
- WordTraceId: 161705
- atomic: true
- Legal Obligation: mandatory
- implement: true
- implementerEnhanced: For all
  [LOOP]
  locations not covered by the gradient profile, the on-board shall consider the gradient value as:
- kind: ordinary

###### 3.13.4.1.3.a (Requirement Type)
the default gradient for TSR, if available and if the concerned target is due to a TSR
- WordTraceId: 161811
- atomic: true
- Legal Obligation: unknown
- implement: true
- implementerEnhanced: the default gradient for TSR,
  if
  [CONDITION]
  available and
  if
  [CONDITION]
  the concerned target is due to a TSR
- ListNumberText: a)
- kind: ordinary

###### 3.13.4.1.3.b (Requirement Type)
zero, for other cases.
- WordTraceId: 161898
- atomic: true
- Legal Obligation: unknown
- implement: true
- ListNumberText: b)
- kind: ordinary

##### 3.13.4.2 (Requirement Type)
Train length compensation
- WordTraceId: 161921
- atomic: false
- Legal Obligation: not applicable
- implement: false
- kind: Heading

###### 3.13.4.2.1 (Requirement Type)
Assuming that a fictive train front end would be at any location between the current (actual) train front end location and the SvL, the acceleration due to the gradient shall be determined using the lowest (taking the sign into account) gradient value given by the gradient profile between the location of the fictive train front end and the location of the fictive train rear end (see Figure 35).
- WordTraceId: 161947
- atomic: true
- Legal Obligation: mandatory
- implement: true
- kind: ordinary
- CrossRefLink -> 3.13.4.1.1[2].[f]35.C

##### 3.13.4.3 (Requirement Type)
Rotating mass
- WordTraceId: 162371
- atomic: false
- Legal Obligation: not applicable
- implement: false
- kind: Heading

###### 3.13.4.3.1 (Requirement Type)
The influence of gradients shall be compensated for the rotating mass of the train (see Figure 35).
- WordTraceId: 162385
- atomic: true
- Legal Obligation: mandatory
- implement: true
- kind: ordinary
- CrossRefLink -> 3.13.4.1.1[2].[f]35.C

###### 3.13.4.3.1.1 (Requirement Type)
Note: Since the rotating mass works like a flywheel (rotating inertia), the effect of the gradient is reduced. Assume for instance a (theoretical) train without any rotating mass, not braking, on a downhill gradient from height 1 to height 2. All the energy added to the train when it goes from H1 to H2 is converted into linear forward motion. This can be observed as an acceleration due to the gradient. Now assume the same train with part of the weight rotating. If this train travels the same distance from H1 to H2, the same amount of energy is added to the train. But now a part of that energy is converted into rotational motion and only the remaining part is converted into linear forward motion. The latter can be observed as an acceleration which is less than for the train without rotating mass.
- WordTraceId: 162511
- atomic: false
- Legal Obligation: not applicable
- implement: false
- implementerEnhanced: Note: Since the rotating mass works like a flywheel (rotating inertia), the effect of the gradient is reduced. Assume for instance a (theoretical) train without any rotating mass, not braking, on a downhill gradient from height 1 to height 2. All the energy added to the train
  when
  [CONDITION]
  it goes from H1 to H2 is converted into linear forward motion. This can be observed as an acceleration due to the gradient. Now assume the same train with part of the weight rotating.
  If
  [CONDITION]
  this train travels the same distance from H1 to H2, the same amount of energy is added to the train. But now a part of that energy is converted into rotational motion and only the remaining part is converted into linear forward motion. The latter can be observed as an acceleration which is less than for the train without rotating mass.
- kind: Note

###### 3.13.4.3.1.2 (Requirement Type)
Note: For the influence of the rotating mass on the deceleration due to the brake, it is already taken into account in the values for the brake parameters.
- WordTraceId: 163318
- atomic: false
- Legal Obligation: not applicable
- implement: false
- kind: Note

###### 3.13.4.3.2 (Requirement Type)
The following formulas shall be used:
- WordTraceId: 163474
- atomic: true
- Legal Obligation: not applicable
- implement: false
- kind: Heading

###### 3.13.4.3.2.a (Requirement Type)
If M_rotating_nom is unknown:
- WordTraceId: 163512
- atomic: true
- Legal Obligation: mandatory
- implement: true
- implementerEnhanced: If
  [CONDITION]
  M_rotating_nom is unknown:
- ListNumberText: a)
- kind: ordinary

###### 3.13.4.3.2.a.*[1] (Requirement Type)
Uphill: A_gradient = g * grad / (1000+10*M_rotating_max)
- WordTraceId: 163542
- atomic: true
- Legal Obligation: mandatory
- implement: true
- ListNumberText: ·
- kind: ordinary

###### 3.13.4.3.2.a.*[2] (Requirement Type)
Downhill: A_gradient = g * grad / (1000+10*M_rotating_min)
- WordTraceId: 163599
- atomic: true
- Legal Obligation: mandatory
- implement: true
- ListNumberText: ·
- kind: ordinary

###### 3.13.4.3.2.b (Requirement Type)
If M_rotating_nom is known:
- WordTraceId: 163658
- atomic: true
- Legal Obligation: mandatory
- implement: true
- implementerEnhanced: If
  [CONDITION]
  M_rotating_nom is known:
- ListNumberText: b)
- kind: ordinary

###### 3.13.4.3.2.b.*[1] (Requirement Type)
Uphill: A_gradient = g * grad / (1000+10*M_rotating_nom)
- WordTraceId: 163686
- atomic: true
- Legal Obligation: mandatory
- implement: true
- ListNumberText: ·
- kind: ordinary

###### 3.13.4.3.2.b.*[2] (Requirement Type)
Downhill: A_gradient = g * grad / (1000+10*M_rotating_nom)
- WordTraceId: 163743
- atomic: true
- Legal Obligation: mandatory
- implement: true
- ListNumberText: ·
- kind: ordinary

###### 3.13.4.3.2[2] (Requirement Type)
Legend:
- WordTraceId: 163802
- atomic: true
- Legal Obligation: unknown
- implement: true
- kind: ordinary

###### 3.13.4.3.2[3] (Requirement Type)
A_gradient = acceleration/deceleration due to gradient
- WordTraceId: 163810
- atomic: true
- Legal Obligation: unknown
- implement: true
- kind: ordinary

###### 3.13.4.3.2[4] (Requirement Type)
g = 9.81 m/s 2 - acceleration of gravity in m/s 2
- WordTraceId: 163865
- atomic: true
- Legal Obligation: unknown
- PlainText: g = 9.81 m/s2 - acceleration of gravity in m/s2
- implement: true
- kind: ordinary

###### 3.13.4.3.2[5] (Requirement Type)
grad = gradient values in ‰ (positive = uphill)
- WordTraceId: 163913
- atomic: true
- Legal Obligation: unknown
- implement: true
- kind: ordinary

###### 3.13.4.3.2[6] (Requirement Type)
M_rotating_nom = nominal rotating mass (part of train data) as a percentage of the total train weight
- WordTraceId: 163961
- atomic: true
- Legal Obligation: unknown
- implement: true
- kind: ordinary

###### 3.13.4.3.2[7] (Requirement Type)
M_rotating_max = maximum possible rotating mass (see A3.1) as a percentage of the total train weight
- WordTraceId: 164063
- atomic: true
- Legal Obligation: unknown
- implement: true
- kind: ordinary
- CrossRefLink -> A.3.1

###### 3.13.4.3.2[8] (Requirement Type)
M_rotating_min = minimum possible rotating mass (see A3.1) as a percentage of the total train weight
- WordTraceId: 164164
- atomic: true
- Legal Obligation: unknown
- implement: true
- kind: ordinary
- CrossRefLink -> A.3.1

#### 3.13.5 (Requirement Type)
Determination of locations without special brake contribution and with reduced adhesion conditions
- WordTraceId: 164265
- atomic: false
- Legal Obligation: not applicable
- implement: false
- kind: Heading

##### 3.13.5.1 (Requirement Type)
As long as it uses a track condition profile given by trackside, the on-board shall consider locations without special brake contribution over a distance going from the start location of the profile to the foot of the deceleration curve (EBD, SBD or GUI, see sections 3.13.8.3, 3.13.8.4 and 3.13.8.5).
- WordTraceId: 164364
- atomic: true
- Legal Obligation: mandatory
- implement: true
- implementerEnhanced: As long as
  [TIME]
  it uses a track condition profile given by
  trackside
  [EXTERNAL]
  , the on-board shall consider locations without special brake contribution over a distance going from the start location of the profile to the foot of the deceleration curve (EBD, SBD or GUI, see sections 3.13.8.3, 3.13.8.4 and 3.13.8.5).
- kind: ordinary
- CrossRefLink -> 3.13.8.3
- CrossRefLink -> 3.13.8.4
- CrossRefLink -> 3.13.8.5

##### 3.13.5.2 (Requirement Type)
If the status of a special brake is “not active”, all locations shall be considered without the contribution of this special brake.
- WordTraceId: 164753
- atomic: true
- Legal Obligation: mandatory
- implement: true
- implementerEnhanced: If
  [CONDITION]
  the status of a special brake is “not active”, all locations shall be considered without the contribution of this special brake.
- kind: ordinary

###### 3.13.5.2.1 (Requirement Type)
Note: in such case, a track condition profile implying the inhibition of this special brake will have no effect.
- WordTraceId: 164885
- atomic: false
- Legal Obligation: not applicable
- implement: false
- kind: Note

##### 3.13.5.3 (Requirement Type)
From the adhesion profile given by trackside, the on-board shall consider locations with reduced adhesion conditions over a distance going from the start location of the profile to the location derived by adding the train length to the end location of the profile.
- WordTraceId: 164998
- atomic: true
- Legal Obligation: mandatory
- implement: true
- implementerEnhanced: From the adhesion profile given by
  trackside
  [EXTERNAL]
  , the on-board shall consider locations with reduced adhesion conditions over a distance going from the start location of the profile to the location derived by adding the train length to the end location of the profile.
- kind: ordinary

##### 3.13.5.4 (Requirement Type)
When slippery rail is selected by the driver, all locations shall be considered with reduced adhesion conditions.
- WordTraceId: 165263
- atomic: true
- Legal Obligation: mandatory
- implement: true
- implementerEnhanced: When
  [CONDITION]
  slippery rail is selected by the
  driver
  [EXTERNAL]
  , all locations shall be considered with reduced adhesion conditions.
- kind: ordinary

##### 3.13.5.5 (Requirement Type)
The speed and distance monitoring shall use, as resulting reduced adhesion conditions, the most restrictive value of the adhesion conditions selected by the driver and the adhesion conditions calculated from the trackside profile.
- WordTraceId: 165377
- atomic: true
- Legal Obligation: mandatory
- implement: true
- implementerEnhanced: The speed and distance monitoring shall use, as resulting reduced adhesion conditions, the most restrictive value of the adhesion conditions selected by the
  driver
  [EXTERNAL]
  and the adhesion conditions calculated from the
  trackside
  [EXTERNAL]
  profile.
- kind: ordinary

#### 3.13.6 (Requirement Type)
Calculation of the deceleration and brake build up time
- WordTraceId: 165608
- atomic: false
- Legal Obligation: not applicable
- implement: false
- implementerEnhanced: Calculation of the deceleration and brake build up
  time
  [TIME]
- kind: Heading

##### 3.13.6.1 (Requirement Type)
Introduction
- WordTraceId: 165664
- atomic: false
- Legal Obligation: not applicable
- implement: false
- kind: Heading

###### 3.13.6.1.1 (Requirement Type)
This chapter describes how the safe emergency brake, the expected and the normal service brake decelerations and the time intervals due to brake build up time are calculated.
- WordTraceId: 165677
- atomic: true
- Legal Obligation: unknown
- implement: false
- implementerEnhanced: This chapter describes how the safe emergency brake, the expected and the normal service brake decelerations and the
  time
  [TIME]
  intervals due to brake build up
  time
  [TIME]
  are calculated.
- kind: Definition

##### 3.13.6.2 (Requirement Type)
Emergency brake
- WordTraceId: 165852
- atomic: false
- Legal Obligation: not applicable
- implement: false
- kind: Heading

###### 3.13.6.2.1 (Requirement Type)
Safe deceleration
- WordTraceId: 165868
- atomic: false
- Legal Obligation: not applicable
- implement: false
- kind: Heading

###### 3.13.6.2.1.1 (Requirement Type)
The safe deceleration, A_safe(V,d), is safety relevant. This means that for the calculation of the safe deceleration, all necessary track and train characteristics shall be taken into account.
- WordTraceId: 165886
- atomic: false
- Legal Obligation: mandatory
- implement: true
- implementerEnhanced: The safe deceleration, A_safe(V,d), is safety relevant. This means that for the calculation of the safe deceleration,
  all necessary
  [WEAK]
  track and train characteristics shall be taken into account.
- kind: ordinary

###### 3.13.6.2.1.2 (Requirement Type)
The train and track related characteristics to be considered are:
- WordTraceId: 166079
- atomic: true
- Legal Obligation: unknown
- implement: false
- kind: Heading

###### 3.13.6.2.1.2.a (Requirement Type)
The speed dependent deceleration model(s) for the emergency brake either acquired as part of Train Data (see 3.13.2.2.3.1) or derived from the brake percentage using the conversion model (see 3.13.3.3)
- WordTraceId: 166145
- atomic: true
- Legal Obligation: unknown
- implement: true
- ListNumberText: a)
- kind: ordinary
- CrossRefLink -> 3.13.2.2.3.1
- CrossRefLink -> 3.13.3.3

###### 3.13.6.2.1.2.b (Requirement Type)
The acceleration/deceleration due to gradient i.e. A_gradient(d) (see 3.13.4)
- WordTraceId: 166405
- atomic: false
- Legal Obligation: unknown
- implement: true
- ListNumberText: b)
- kind: ordinary
- CrossRefLink -> 3.13.4

###### 3.13.6.2.1.2.c (Requirement Type)
The locations with reduced adhesion conditions (see 3.13.5)
- WordTraceId: 166512
- atomic: true
- Legal Obligation: unknown
- implement: true
- ListNumberText: c)
- kind: ordinary
- CrossRefLink -> 3.13.5

###### 3.13.6.2.1.2.d (Requirement Type)
The National Values for reduced adhesion condition (see 3.13.2.3.7.7)
- WordTraceId: 166601
- atomic: true
- Legal Obligation: unknown
- implement: true
- ListNumberText: d)
- kind: ordinary
- CrossRefLink -> 3.13.2.3.7.7

###### 3.13.6.2.1.2.e (Requirement Type)
The locations without special brake contribution (see 3.13.5), only if the speed dependent deceleration model(s) for the emergency brake are acquired as part of Train Data
- WordTraceId: 166700
- atomic: true
- Legal Obligation: unknown
- implement: true
- implementerEnhanced: The locations without special brake contribution (see 3.13.5), only
  if
  [CONDITION]
  the speed dependent deceleration model(s) for the emergency brake are acquired as part of Train Data
- ListNumberText: e)
- kind: ordinary
- CrossRefLink -> 3.13.5

###### 3.13.6.2.1.2.f (Requirement Type)
The rolling stock correction factors Kdry_rst(V, EBCL) and Kwet_rst(V) (see 3.13.2.2.9.1), only if the speed dependent deceleration model(s) for the emergency brake are acquired as part of Train Data
- WordTraceId: 166901
- atomic: true
- Legal Obligation: unknown
- implement: true
- implementerEnhanced: The rolling stock correction factors Kdry_rst(V, EBCL) and Kwet_rst(V) (see 3.13.2.2.9.1), only
  if
  [CONDITION]
  the speed dependent deceleration model(s) for the emergency brake are acquired as part of Train Data
- ListNumberText: f)
- kind: ordinary
- CrossRefLink -> 3.13.2.2.9.1

###### 3.13.6.2.1.2.g (Requirement Type)
The National Values for confidence level on emergency brake safe deceleration and for the available wheel/rail adhesion (see 3.13.2.3.7.5 & 3.13.2.3.7.6), only if the speed dependent deceleration model(s) for the emergency brake are acquired as part of Train Data
- WordTraceId: 167130
- atomic: true
- Legal Obligation: unknown
- implement: true
- implementerEnhanced: The National Values for confidence level on emergency brake safe deceleration and for the available wheel/rail adhesion (see 3.13.2.3.7.5 & 3.13.2.3.7.6), only
  if
  [CONDITION]
  the speed dependent deceleration model(s) for the emergency brake are acquired as part of Train Data
- ListNumberText: g)
- kind: ordinary
- CrossRefLink -> 3.13.2.3.7.5
- CrossRefLink -> 3.13.2.3.7.6

###### 3.13.6.2.1.2.h (Requirement Type)
The integrated correction factors Kv_int(V) (with the two pivot deceleration values for passenger trains) and Kr_int(l) (see 3.13.2.3.7), only if the conversion model is used
- WordTraceId: 167452
- atomic: true
- Legal Obligation: unknown
- implement: true
- implementerEnhanced: The integrated correction factors Kv_int(V) (with the two pivot deceleration values for passenger trains) and Kr_int(l) (see 3.13.2.3.7), only
  if
  [CONDITION]
  the conversion model is used
- ListNumberText: h)
- kind: ordinary
- CrossRefLink -> 3.13.2.3.7

###### 3.13.6.2.1.2.i (Requirement Type)
The brake position (see 3.13.2.2.4)
- WordTraceId: 167656
- atomic: true
- Legal Obligation: unknown
- implement: true
- ListNumberText: i)
- kind: ordinary
- CrossRefLink -> 3.13.2.2.4

###### 3.13.6.2.1.2.j (Requirement Type)
The acquired train length L_TRAIN (see 3.13.2.2.11), only if the conversion model is used
- WordTraceId: 167721
- atomic: true
- Legal Obligation: unknown
- implement: true
- implementerEnhanced: The acquired train length L_TRAIN (see 3.13.2.2.11), only
  if
  [CONDITION]
  the conversion model is used
- ListNumberText: j)
- kind: ordinary
- CrossRefLink -> 3.13.2.2.11

###### 3.13.6.2.1.3 (Requirement Type)
A_safe(V,d) shall be equal to:
- WordTraceId: 167841
- atomic: true
- Legal Obligation: mandatory
- implement: true
- kind: ordinary

###### 3.13.6.2.1.3[2] (Requirement Type)
For locations with normal adhesion conditions:
- WordTraceId: 167872
- atomic: true
- Legal Obligation: unknown
- implement: true
- kind: ordinary

###### 3.13.6.2.1.3[3] (Requirement Type)
A_safe(V,d) = A_brake_safe(V,d) + A_gradient(d)
- WordTraceId: 167919
- atomic: true
- Legal Obligation: unknown
- implement: true
- kind: ordinary

###### 3.13.6.2.1.3[4] (Requirement Type)
For locations with reduced adhesion conditions:
- WordTraceId: 167967
- atomic: true
- Legal Obligation: unknown
- implement: true
- kind: ordinary

###### 3.13.6.2.1.3[5] (Requirement Type)
A_safe(V,d) = MIN(A_brake_safe(V,d) , A_MAXREDADH) + A_gradient(d)
- WordTraceId: 168015
- atomic: true
- Legal Obligation: unknown
- implement: true
- kind: ordinary

###### 3.13.6.2.1.4 (Requirement Type)
A_brake_safe(V,d) shall be the safe emergency brake deceleration. A_brake_safe(V,d) shall be equal to:
- WordTraceId: 168082
- atomic: false
- Legal Obligation: mandatory
- implement: true
- kind: ordinary

###### 3.13.6.2.1.4[2] (Requirement Type)
If the speed dependent deceleration model(s) for the emergency brake are acquired as part of Train Data:
- WordTraceId: 168185
- atomic: true
- Legal Obligation: unknown
- implement: true
- implementerEnhanced: If
  [CONDITION]
  the speed dependent deceleration model(s) for the emergency brake are acquired as part of Train Data:
- kind: ordinary

###### 3.13.6.2.1.4[3] (Requirement Type)
A_brake_safe(V,d) = Kdry_rst(V, M_NVEBCL) * (Kwet_rst(V) + M_NVAVADH *(1- Kwet_rst(V))) * A_brake_emergency(V,d)
- WordTraceId: 168290
- atomic: true
- Legal Obligation: unknown
- implement: true
- kind: ordinary

###### 3.13.6.2.1.4[4] (Requirement Type)
If the conversion model is used:
- WordTraceId: 168403
- atomic: true
- Legal Obligation: unknown
- implement: true
- implementerEnhanced: If
  [CONDITION]
  the conversion model is used:
- kind: ordinary

###### 3.13.6.2.1.4[5] (Requirement Type)
A_brake_safe(V) = Kv_int(V) * Kr_int(L_TRAIN) * A_brake_emergency(V)
- WordTraceId: 168436
- atomic: true
- Legal Obligation: unknown
- implement: true
- kind: ordinary

###### 3.13.6.2.1.5 (Requirement Type)
A_brake_emergency(V,d) shall be the emergency brake deceleration as a function of the speed, of the
locations with change of special brake(s) contribution encountered between the train front and the foot of the EBD curve. A_brake_emergency(V,d) shall be equal to:
- WordTraceId: 168505
- atomic: false
- Legal Obligation: mandatory
- implement: true
- kind: ordinary

###### 3.13.6.2.1.5[2] (Requirement Type)
A_brake_emergency 1 (V) when d estfront ≤ d ≤ d 1
- WordTraceId: 168769
- atomic: true
- Legal Obligation: unknown
- PlainText: A_brake_emergency1(V) when destfront ≤ d ≤ d1
- implement: true
- implementerEnhanced: A_brake_emergency1(V)
  when
  [CONDITION]
  destfront ≤ d ≤ d1
- kind: ordinary

###### 3.13.6.2.1.5[3] (Requirement Type)
A_brake_emergency 2 (V) when d 1 < d ≤ d 2
- WordTraceId: 168815
- atomic: true
- Legal Obligation: unknown
- PlainText: A_brake_emergency2(V) when d1 < d ≤ d2
- implement: true
- implementerEnhanced: A_brake_emergency2(V)
  when
  [CONDITION]
  d1 < d ≤ d2
- kind: ordinary

###### 3.13.6.2.1.5[4] (Requirement Type)
A_brake_emergency 3 (V) when d 2 < d ≤ d 3
- WordTraceId: 168854
- atomic: true
- Legal Obligation: unknown
- PlainText: A_brake_emergency3(V) when d2 < d ≤ d3
- implement: true
- implementerEnhanced: A_brake_emergency3(V)
  when
  [CONDITION]
  d2 < d ≤ d3
- kind: ordinary

###### 3.13.6.2.1.5[5] (Requirement Type)
....
- WordTraceId: 168893
- atomic: true
- Legal Obligation: unknown
- implement: true
- implementerEnhanced: ...
  [WEAK]
  .
- kind: ordinary

###### 3.13.6.2.1.5[6] (Requirement Type)
Where
- WordTraceId: 168898
- atomic: true
- Legal Obligation: unknown
- implement: true
- kind: ordinary

###### 3.13.6.2.1.5[7] (Requirement Type)
d 1 , d 2 , d 3 ,... are the locations with change of special brake(s) contribution
- WordTraceId: 168904
- atomic: true
- Legal Obligation: unknown
- PlainText: d1, d2, d3,... are the locations with change of special brake(s) contribution
- implement: true
- implementerEnhanced: d1, d2, d3,
  ...
  [WEAK]
  are the locations with change of special brake(s) contribution
- kind: ordinary

###### 3.13.6.2.1.5[8] (Requirement Type)
A_brake_emergency x (V) is equal to the emergency brake model, A_brake_emergency, applicable for the concerned combination of brake.
- WordTraceId: 168982
- atomic: true
- Legal Obligation: unknown
- PlainText: A_brake_emergencyx(V) is equal to the emergency brake model, A_brake_emergency, applicable for the concerned combination of brake.
- implement: true
- kind: ordinary

###### 3.13.6.2.1.5[9] (Requirement Type)
- WordTraceId: 169113
- atomic: false
- Legal Obligation: not applicable
- implement: false
- kind: Placeholder

###### 3.13.6.2.1.5[9].[f]36 (Requirement Type)
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- WordTraceId: 169141
- atomic: false
- Legal Obligation: not applicable
- implement: false
- kind: Figure

###### 3.13.6.2.1.5[9].[f]36.C (Requirement Type)
Figure {Figure 36}: Influence of track conditions on A_brake_emergency(V,d)
- WordTraceId: 169141
- atomic: true
- Legal Obligation: unknown
- PlainText: Figure 36: Influence of track conditions on A_brake_emergency(V,d)
- implement: false
- kind: Figure

###### 3.13.6.2.1.6 (Requirement Type)
A_MAXREDADH shall be the deceleration value, out of the three related National Values, applicable for this train according to:
- WordTraceId: 169233
- atomic: true
- Legal Obligation: mandatory
- implement: true
- kind: ordinary

###### 3.13.6.2.1.6.a (Requirement Type)
its brake position
- WordTraceId: 169360
- atomic: true
- Legal Obligation: unknown
- implement: true
- ListNumberText: a)
- kind: ordinary

###### 3.13.6.2.1.6.b (Requirement Type)
whether special/additional brakes independent from wheel/rail adhesion are active and it is allowed to take into account their contribution to the emergency braking effort.
- WordTraceId: 169379
- atomic: true
- Legal Obligation: unknown
- implement: true
- implementerEnhanced: whether
  [CONDITION]
  special/additional brakes independent from wheel/rail adhesion are active and it is allowed to take into account their contribution to the emergency braking effort.
- ListNumberText: b)
- kind: ordinary

###### 3.13.6.2.1.7 (Requirement Type)
Kdry_rst(V, M_NVEBCL) shall be the rolling stock correction factor, as a function of speed (with speed steps identical with the ones of A_brake_emergency(V)), corresponding to the confidence level on emergency brake safe deceleration required by trackside (National Value).
- WordTraceId: 169552
- atomic: true
- Legal Obligation: mandatory
- implement: true
- implementerEnhanced: Kdry_rst(V, M_NVEBCL) shall be the rolling stock correction factor, as a function of speed (with speed steps identical with the ones of A_brake_emergency(V)), corresponding to the confidence level on emergency brake safe deceleration required by
  trackside
  [EXTERNAL]
  (National Value).
- kind: ordinary

###### 3.13.6.2.1.8 (Requirement Type)
Kv_int(V) shall be the integrated correction factor applicable for the train, selected according to the brake position.
- WordTraceId: 169826
- atomic: true
- Legal Obligation: mandatory
- implement: true
- kind: ordinary

###### 3.13.6.2.1.8.1 (Requirement Type)
If the brake position is “Passenger train in P”, the set of Kv_int shall be calculated as a function of the maximum emergency brake deceleration (A_ebmax) in the following way (see also figure 10):
- WordTraceId: 169946
- atomic: true
- Legal Obligation: mandatory
- implement: true
- implementerEnhanced: If
  [CONDITION]
  the brake position is “
  Passenger train in P
  [LINKED_PHRASE]
  ”, the set of Kv_int shall be calculated as a function of the maximum emergency brake deceleration (A_ebmax) in the following way (see also figure 10):
- kind: ordinary
- CrossRefLink -> 3.6.2.3.1.1.*[2][2].[f]10.C
- KnownTermLink -> 3.13.2.2.3.1.9.b

###### 3.13.6.2.1.8.1[2] (Requirement Type)
Kv_int_x = Kv_int_x_a when A_ebmax ≤ A_P12.
- WordTraceId: 170144
- atomic: true
- Legal Obligation: unknown
- implement: true
- implementerEnhanced: Kv_int_x = Kv_int_x_a
  when
  [CONDITION]
  A_ebmax ≤ A_P12.
- kind: ordinary

###### 3.13.6.2.1.8.1[3] (Requirement Type)
Kv_int_x = Kv_int_x_b when A_ebmax ≥ A_P23.
- WordTraceId: 170190
- atomic: true
- Legal Obligation: unknown
- implement: true
- implementerEnhanced: Kv_int_x = Kv_int_x_b
  when
  [CONDITION]
  A_ebmax ≥ A_P23.
- kind: ordinary

###### 3.13.6.2.1.8.1[4] (Requirement Type)
Kv_int_x = Kv_int_x_a + (A_ebmax - A_P12)/(A_P23 - A_P12) * (Kv_int_x_b - Kv_int_x_a) when A_P12 < A_ebmax < A_P23.”
- WordTraceId: 170236
- atomic: true
- Legal Obligation: unknown
- implement: true
- implementerEnhanced: Kv_int_x = Kv_int_x_a + (A_ebmax - A_P12)/(A_P23 - A_P12) * (Kv_int_x_b - Kv_int_x_a)
  when
  [CONDITION]
  A_P12 < A_ebmax < A_P23.”
- kind: ordinary

###### 3.13.6.2.1.8.1[5] (Requirement Type)
- WordTraceId: 170354
- atomic: false
- Legal Obligation: not applicable
- implement: false
- kind: Placeholder

###### 3.13.6.2.1.8.1[5].[f]37 (Requirement Type)
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- WordTraceId: 170382
- atomic: false
- Legal Obligation: not applicable
- implement: false
- kind: Figure

###### 3.13.6.2.1.8.1[5].[f]37.C (Requirement Type)
Figure {Figure 37}: Kv_int structure for conventional passenger trains
- WordTraceId: 170382
- atomic: true
- Legal Obligation: unknown
- PlainText: Figure 37: Kv_int structure for conventional passenger trains
- implement: false
- kind: Figure

###### 3.13.6.2.1.8.2 (Requirement Type)
The maximum EB deceleration A_ebmax shall be the maximum of A_brake_emergency between 0 km/h and the maximum speed of the train.
- WordTraceId: 170469
- atomic: true
- Legal Obligation: mandatory
- implement: true
- kind: ordinary

###### 3.13.6.2.1.9 (Requirement Type)
Note: Figure 38 gives an example of the influence of the various track/train characteristics on A_safe(V,d) and consequently on the EBD curve (see 3.13.8.3).
- WordTraceId: 170598
- atomic: false
- Legal Obligation: not applicable
- implement: false
- kind: Note
- CrossRefLink -> 3.13.6.2.1.9[2].[f]38.C
- CrossRefLink -> 3.13.8.3

###### 3.13.6.2.1.9[2] (Requirement Type)
- WordTraceId: 170827
- atomic: false
- Legal Obligation: not applicable
- implement: false
- kind: Placeholder

###### 3.13.6.2.1.9[2].[f]38 (Requirement Type)
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- WordTraceId: 170855
- atomic: false
- Legal Obligation: not applicable
- implement: false
- kind: Figure

###### 3.13.6.2.1.9[2].[f]38.C (Requirement Type)
Figure {Figure 38}: Influence of track/train characteristics on A_safe
- WordTraceId: 170855
- atomic: true
- Legal Obligation: unknown
- PlainText: Figure 38: Influence of track/train characteristics on A_safe
- implement: false
- kind: Figure

###### 3.13.6.2.2 (Requirement Type)
Safe brake build up time
- WordTraceId: 170942
- atomic: false
- Legal Obligation: not applicable
- implement: false
- implementerEnhanced: Safe brake build up
  time
  [TIME]
- kind: Heading

###### 3.13.6.2.2.1 (Requirement Type)
The safe brake build up time, T_be, is safety relevant. This means that for the calculation of the safe brake build up time, all necessary track and train characteristics shall be taken into account.
- WordTraceId: 170967
- atomic: false
- Legal Obligation: mandatory
- implement: true
- implementerEnhanced: The safe brake build up
  time
  [TIME]
  , T_be, is safety relevant. This means that for the calculation of the safe brake build up
  time
  [TIME]
  ,
  all necessary
  [WEAK]
  track and train characteristics shall be taken into account.
- kind: ordinary

###### 3.13.6.2.2.2 (Requirement Type)
The train and track related characteristics to be considered are:
- WordTraceId: 171167
- atomic: true
- Legal Obligation: unknown
- implement: false
- kind: Heading

###### 3.13.6.2.2.2.a (Requirement Type)
The values of T_brake_emergency acquired as part of Train Data (see 3.13.2.2.3.2.8) or the value of T_brake_emergency derived from the conversion model (see 3.13.3.4) using the brake position and train length acquired as Train Data.
- WordTraceId: 171233
- atomic: true
- Legal Obligation: unknown
- implement: true
- ListNumberText: a)
- kind: ordinary
- CrossRefLink -> 3.13.2.2.3.2.8
- CrossRefLink -> 3.13.3.4

###### 3.13.6.2.2.2.b (Requirement Type)
The integrated correction factor Kt_int, only if the conversion model is used (see 3.13.2.3.7)
- WordTraceId: 171524
- atomic: true
- Legal Obligation: unknown
- implement: true
- implementerEnhanced: The integrated correction factor Kt_int, only
  if
  [CONDITION]
  the conversion model is used (see 3.13.2.3.7)
- ListNumberText: b)
- kind: ordinary
- CrossRefLink -> 3.13.2.3.7

###### 3.13.6.2.2.2.c (Requirement Type)
The status of the regenerative brake, eddy current brake, magnetic shoe brake and Ep brake system (see 3.13.2.2.6), only if the values of T_brake_emergency are acquired as part of Train Data
- WordTraceId: 171649
- atomic: true
- Legal Obligation: unknown
- implement: true
- implementerEnhanced: The status of the regenerative brake, eddy current brake, magnetic shoe brake and Ep brake system (see 3.13.2.2.6), only
  if
  [CONDITION]
  the values of T_brake_emergency are acquired as part of Train Data
- ListNumberText: c)
- kind: ordinary
- CrossRefLink -> 3.13.2.2.5.2

###### 3.13.6.2.2.3 (Requirement Type)
The safe brake build up time T_be shall be equal to:
- WordTraceId: 171869
- atomic: true
- Legal Obligation: mandatory
- implement: true
- implementerEnhanced: The safe brake build up
  time
  [TIME]
  T_be shall be equal to:
- kind: ordinary

###### 3.13.6.2.2.3[2] (Requirement Type)
If values of T_brake_emergency are acquired as part of Train Data:
- WordTraceId: 171922
- atomic: true
- Legal Obligation: unknown
- implement: true
- implementerEnhanced: If
  [CONDITION]
  values of T_brake_emergency are acquired as part of Train Data:
- kind: ordinary

###### 3.13.6.2.2.3[3] (Requirement Type)
T_be = T_brake_emergency, with T_brake_emergency corresponding to the combination of special brakes currently in use
- WordTraceId: 171989
- atomic: true
- Legal Obligation: unknown
- implement: true
- kind: ordinary

###### 3.13.6.2.2.3[4] (Requirement Type)
If the conversion model is used:
- WordTraceId: 172106
- atomic: true
- Legal Obligation: unknown
- implement: true
- implementerEnhanced: If
  [CONDITION]
  the conversion model is used:
- kind: ordinary

###### 3.13.6.2.2.3[5] (Requirement Type)
T_be = Kt_int * T_brake_emergency
- WordTraceId: 172139
- atomic: true
- Legal Obligation: unknown
- implement: true
- kind: ordinary

##### 3.13.6.3 (Requirement Type)
Service brake
- WordTraceId: 172173
- atomic: false
- Legal Obligation: not applicable
- implement: false
- kind: Heading

###### 3.13.6.3.1 (Requirement Type)
Expected deceleration
- WordTraceId: 172187
- atomic: false
- Legal Obligation: not applicable
- implement: false
- kind: Heading

###### 3.13.6.3.1.1 (Requirement Type)
Since the expected deceleration is not safety relevant, no worst case conditions (e.g. correction factors, adhesion conditions) need to be taken into account for its calculation.
- WordTraceId: 172209
- atomic: true
- Legal Obligation: unknown
- implement: true
- implementerEnhanced: Since the expected deceleration is not safety relevant, no
  worst
  [WEAK]
  case conditions (
  e.g.
  [WEAK]
  correction factors, adhesion conditions) need to be taken into account for its calculation.
- kind: ordinary

###### 3.13.6.3.1.2 (Requirement Type)
The train and track related characteristics to be considered are:
- WordTraceId: 172388
- atomic: true
- Legal Obligation: unknown
- implement: false
- kind: Heading

###### 3.13.6.3.1.2.a (Requirement Type)
The speed dependent deceleration model(s) for the full service brake either acquired as part of Train Data (see 3.13.2.2.3.1) or derived from the brake percentage using the conversion model (see 3.13.3.3)
- WordTraceId: 172454
- atomic: true
- Legal Obligation: unknown
- implement: true
- ListNumberText: a)
- kind: ordinary
- CrossRefLink -> 3.13.2.2.3.1
- CrossRefLink -> 3.13.3.3

###### 3.13.6.3.1.2.b (Requirement Type)
The acceleration/deceleration due to gradient i.e. A_gradient(d) (see 3.13.4)
- WordTraceId: 172717
- atomic: false
- Legal Obligation: unknown
- implement: true
- ListNumberText: b)
- kind: ordinary
- CrossRefLink -> 3.13.4

###### 3.13.6.3.1.2.c (Requirement Type)
The locations without special brake contribution (see 3.13.5)
- WordTraceId: 172824
- atomic: true
- Legal Obligation: unknown
- implement: true
- ListNumberText: c)
- kind: ordinary
- CrossRefLink -> 3.13.5

###### 3.13.6.3.1.3 (Requirement Type)
A_expected(V,d) shall be equal to:
- WordTraceId: 172915
- atomic: true
- Legal Obligation: mandatory
- implement: true
- kind: ordinary

###### 3.13.6.3.1.3[2] (Requirement Type)
A_expected(V,d) = A_brake_service(V,d) +A_gradient(d)
- WordTraceId: 172950
- atomic: true
- Legal Obligation: unknown
- implement: true
- kind: ordinary

###### 3.13.6.3.1.4 (Requirement Type)
A_brake_service(V,d) shall be the full deceleration of the service brake as a function of the speed, of the locations with change of special brake(s) contribution encountered between the train front and the foot of the SBD curve. A_brake_service(V,d) shall be equal to:
- WordTraceId: 173004
- atomic: false
- Legal Obligation: mandatory
- implement: true
- kind: ordinary

###### 3.13.6.3.1.4[2] (Requirement Type)
A_brake_service 1 (V) when d estfront ≤ d ≤ d 1
- WordTraceId: 173274
- atomic: true
- Legal Obligation: unknown
- PlainText: A_brake_service1(V) when destfront ≤ d ≤ d1
- implement: true
- implementerEnhanced: A_brake_service1(V)
  when
  [CONDITION]
  destfront ≤ d ≤ d1
- kind: ordinary

###### 3.13.6.3.1.4[3] (Requirement Type)
A_brake_service 2 (V) when d 1 < d ≤ d 2
- WordTraceId: 173318
- atomic: true
- Legal Obligation: unknown
- PlainText: A_brake_service2(V) when d1 < d ≤ d2
- implement: true
- implementerEnhanced: A_brake_service2(V)
  when
  [CONDITION]
  d1 < d ≤ d2
- kind: ordinary

###### 3.13.6.3.1.4[4] (Requirement Type)
A_brake_service 3 (V) when d 2 < d ≤ d 3
- WordTraceId: 173355
- atomic: true
- Legal Obligation: unknown
- PlainText: A_brake_service3(V) when d2 < d ≤ d3
- implement: true
- implementerEnhanced: A_brake_service3(V)
  when
  [CONDITION]
  d2 < d ≤ d3
- kind: ordinary

###### 3.13.6.3.1.4[5] (Requirement Type)
....
- WordTraceId: 173392
- atomic: true
- Legal Obligation: unknown
- implement: true
- implementerEnhanced: ...
  [WEAK]
  .
- kind: ordinary

###### 3.13.6.3.1.4[6] (Requirement Type)
Where
- WordTraceId: 173397
- atomic: true
- Legal Obligation: unknown
- implement: true
- kind: ordinary

###### 3.13.6.3.1.4[7] (Requirement Type)
d 1 , d 2 , d 3 ,... are the locations with change of special brake(s) contribution
- WordTraceId: 173403
- atomic: true
- Legal Obligation: unknown
- PlainText: d1, d2, d3,... are the locations with change of special brake(s) contribution
- implement: true
- implementerEnhanced: d1, d2, d3,
  ...
  [WEAK]
  are the locations with change of special brake(s) contribution
- kind: ordinary

###### 3.13.6.3.1.4[8] (Requirement Type)
A_brake_service x (V) is equal to the full service brake model, A_brake_service, applicable for the concerned combination of brake.
- WordTraceId: 173481
- atomic: true
- Legal Obligation: unknown
- PlainText: A_brake_servicex(V) is equal to the full service brake model, A_brake_service, applicable for the concerned combination of brake.
- implement: true
- kind: ordinary

###### 3.13.6.3.2 (Requirement Type)
Expected brake build up time
- WordTraceId: 173611
- atomic: false
- Legal Obligation: not applicable
- implement: false
- implementerEnhanced: Expected brake build up
  time
  [TIME]
- kind: Heading

###### 3.13.6.3.2.1 (Requirement Type)
Since the expected brake build up time is not safety relevant, no worst case conditions (e.g. correction factors, adhesion conditions) need to be taken into account for its calculation.
- WordTraceId: 173640
- atomic: true
- Legal Obligation: unknown
- implement: true
- implementerEnhanced: Since the expected brake build up
  time
  [TIME]
  is not safety relevant, no
  worst
  [WEAK]
  case conditions (
  e.g.
  [WEAK]
  correction factors, adhesion conditions) need to be taken into account for its calculation.
- kind: ordinary

###### 3.13.6.3.2.2 (Requirement Type)
No track related characteristics are to be considered for the expected brake build up time.
- WordTraceId: 173826
- atomic: true
- Legal Obligation: unknown
- implement: true
- implementerEnhanced: No track related characteristics are to be considered for the expected brake build up
  time
  [TIME]
  .
- kind: ordinary

###### 3.13.6.3.2.3 (Requirement Type)
The train related characteristics to be considered are:
- WordTraceId: 173918
- atomic: true
- Legal Obligation: unknown
- implement: false
- kind: Heading

###### 3.13.6.3.2.3.a (Requirement Type)
The values of T_brake_service acquired as part of Train Data (see 3.13.2.2.3.2.8) or the value(s) of T_brake_service derived from the conversion model (see 3.13.3.4) using the brake position and train length acquired as Train Data)
- WordTraceId: 173974
- atomic: true
- Legal Obligation: unknown
- implement: true
- ListNumberText: a)
- kind: ordinary
- CrossRefLink -> 3.13.2.2.3.2.8
- CrossRefLink -> 3.13.3.4

###### 3.13.6.3.2.3.b (Requirement Type)
The status of the regenerative brake, eddy current brake and Ep brake system (see 3.13.2.2.6)
- WordTraceId: 174264
- atomic: true
- Legal Obligation: unknown
- implement: true
- ListNumberText: b)
- kind: ordinary
- CrossRefLink -> 3.13.2.2.5.2

###### 3.13.6.3.2.4 (Requirement Type)
The expected brake build up time T_bs shall be equal to the brake build up time of the full service brake:
- WordTraceId: 174387
- atomic: true
- Legal Obligation: mandatory
- implement: true
- implementerEnhanced: The expected brake build up
  time
  [TIME]
  T_bs shall be equal to the brake build up
  time
  [TIME]
  of the full service brake:
- kind: ordinary

###### 3.13.6.3.2.4[2] (Requirement Type)
T_bs = T_brake_service, with T_brake_service corresponding to the combination of special brakes currently in use
- WordTraceId: 174494
- atomic: true
- Legal Obligation: unknown
- implement: true
- kind: ordinary

##### 3.13.6.4 (Requirement Type)
Normal service brake deceleration
- WordTraceId: 174607
- atomic: false
- Legal Obligation: not applicable
- implement: false
- kind: Heading

###### 3.13.6.4.1 (Requirement Type)
Since the normal service brake deceleration is not safety relevant, no worst case conditions (e.g. correction factors, adhesion conditions) need to be taken into account for its calculation.
- WordTraceId: 174641
- atomic: true
- Legal Obligation: unknown
- implement: true
- implementerEnhanced: Since the normal service brake deceleration is not safety relevant, no
  worst
  [WEAK]
  case conditions (
  e.g.
  [WEAK]
  correction factors, adhesion conditions) need to be taken into account for its calculation.
- kind: ordinary

###### 3.13.6.4.2 (Requirement Type)
The train and track related characteristics to be considered are:
- WordTraceId: 174832
- atomic: true
- Legal Obligation: unknown
- implement: false
- kind: Heading

###### 3.13.6.4.2.a (Requirement Type)
The speed dependent deceleration model(s) for the full service brake either acquired as part of Train Data (see 3.13.2.2.3.1) or derived from the brake percentage using the conversion model (see 3.13.3.3)
- WordTraceId: 174898
- atomic: true
- Legal Obligation: unknown
- implement: true
- ListNumberText: a)
- kind: ordinary
- CrossRefLink -> 3.13.2.2.3.1
- CrossRefLink -> 3.13.3.3

###### 3.13.6.4.2.b (Requirement Type)
The speed dependent deceleration model(s) for the normal service brake acquired as part of Train Data (see 3.13.2.2.3.1)
- WordTraceId: 175161
- atomic: true
- Legal Obligation: unknown
- implement: true
- ListNumberText: b)
- kind: ordinary
- CrossRefLink -> 3.13.2.2.3.1

###### 3.13.6.4.2.c (Requirement Type)
The acceleration/deceleration due to gradient i.e. A_gradient(d) (see 3.13.4)
- WordTraceId: 175311
- atomic: false
- Legal Obligation: unknown
- implement: true
- ListNumberText: c)
- kind: ordinary
- CrossRefLink -> 3.13.4

###### 3.13.6.4.2.d (Requirement Type)
The brake position (see 3.13.2.2.4)
- WordTraceId: 175418
- atomic: true
- Legal Obligation: unknown
- implement: true
- ListNumberText: d)
- kind: ordinary
- CrossRefLink -> 3.13.2.2.4

###### 3.13.6.4.2.e (Requirement Type)
The on-board correction factors Kn+(V) and Kn-(V) (see 3.13.2.2.9.2)
- WordTraceId: 175483
- atomic: true
- Legal Obligation: unknown
- implement: true
- ListNumberText: e)
- kind: ordinary
- CrossRefLink -> 3.13.2.2.9.2

###### 3.13.6.4.2.f (Requirement Type)
The locations without special brake contribution (see 3.13.5)
- WordTraceId: 175581
- atomic: true
- Legal Obligation: unknown
- implement: true
- ListNumberText: f)
- kind: ordinary
- CrossRefLink -> 3.13.5

###### 3.13.6.4.3 (Requirement Type)
The normal service brake deceleration shall be equal to:
- WordTraceId: 175672
- atomic: true
- Legal Obligation: mandatory
- implement: true
- kind: ordinary

###### 3.13.6.4.3[2] (Requirement Type)
For positive gradient values (uphill):
- WordTraceId: 175729
- atomic: true
- Legal Obligation: unknown
- implement: true
- kind: ordinary

###### 3.13.6.4.3[3] (Requirement Type)
A_normal_service(V,d) = A_brake_normal_service(V,d) + A_gradient(d) – Kn+(V)*grad
- WordTraceId: 175768
- atomic: true
- Legal Obligation: unknown
- implement: true
- kind: ordinary

###### 3.13.6.4.3[4] (Requirement Type)
For negative gradient values (downhill):
- WordTraceId: 175850
- atomic: true
- Legal Obligation: unknown
- implement: true
- kind: ordinary

###### 3.13.6.4.3[5] (Requirement Type)
A_normal_service(V,d) = A_brake_normal_service(V,d) + A_gradient(d) – Kn-(V)*grad
- WordTraceId: 175891
- atomic: true
- Legal Obligation: unknown
- implement: true
- kind: ordinary

###### 3.13.6.4.3[6] (Requirement Type)
Where
- WordTraceId: 175973
- atomic: true
- Legal Obligation: unknown
- implement: true
- kind: ordinary

###### 3.13.6.4.3[7] (Requirement Type)
grad = gradient values in ‰ (positive = uphill)
- WordTraceId: 175979
- atomic: true
- Legal Obligation: unknown
- implement: true
- kind: ordinary

###### 3.13.6.4.4 (Requirement Type)
A_brake_normal_service(V,d) shall be the normal deceleration of the service brake as a function of the speed, of the locations with change of special brake(s) contribution encountered between the train front and the foot of the GUI curve. A_brake_normal_service(V,d) shall be equal to:
- WordTraceId: 176027
- atomic: false
- Legal Obligation: mandatory
- implement: true
- kind: ordinary

###### 3.13.6.4.4[2] (Requirement Type)
A_brake_normal_service 1 (V) when d estfront ≤ d ≤ d 1
- WordTraceId: 176313
- atomic: true
- Legal Obligation: unknown
- PlainText: A_brake_normal_service1(V) when destfront ≤ d ≤ d1
- implement: true
- implementerEnhanced: A_brake_normal_service1(V)
  when
  [CONDITION]
  destfront ≤ d ≤ d1
- kind: ordinary

###### 3.13.6.4.4[3] (Requirement Type)
A_brake_normal_service 2 (V) when d 1 < d ≤ d 2
- WordTraceId: 176364
- atomic: true
- Legal Obligation: unknown
- PlainText: A_brake_normal_service2(V) when d1 < d ≤ d2
- implement: true
- implementerEnhanced: A_brake_normal_service2(V)
  when
  [CONDITION]
  d1 < d ≤ d2
- kind: ordinary

###### 3.13.6.4.4[4] (Requirement Type)
A_brake_normal_service 3 (V) when d 2 < d ≤ d 3
- WordTraceId: 176408
- atomic: true
- Legal Obligation: unknown
- PlainText: A_brake_normal_service3(V) when d2 < d ≤ d3
- implement: true
- implementerEnhanced: A_brake_normal_service3(V)
  when
  [CONDITION]
  d2 < d ≤ d3
- kind: ordinary

###### 3.13.6.4.4[5] (Requirement Type)
....
- WordTraceId: 176452
- atomic: true
- Legal Obligation: unknown
- implement: true
- implementerEnhanced: ...
  [WEAK]
  .
- kind: ordinary

###### 3.13.6.4.4[6] (Requirement Type)
Where
- WordTraceId: 176457
- atomic: true
- Legal Obligation: unknown
- implement: true
- kind: ordinary

###### 3.13.6.4.4[7] (Requirement Type)
d 1 , d 2 , d 3 ,... are the locations with change of special brake(s) contribution
- WordTraceId: 176463
- atomic: true
- Legal Obligation: unknown
- PlainText: d1, d2, d3,... are the locations with change of special brake(s) contribution
- implement: true
- implementerEnhanced: d1, d2, d3,
  ...
  [WEAK]
  are the locations with change of special brake(s) contribution
- kind: ordinary

###### 3.13.6.4.4[8] (Requirement Type)
A_brake_normal_service x (V) is equal to the normal service brake model applicable for the concerned combination of brake position and of the value of A_brake_service(V=0) between d x-1 and d x (see 3.13.2.2.3.1.9 and 3.13.2.2.3.1.10).
- WordTraceId: 176541
- atomic: true
- Legal Obligation: unknown
- PlainText: A_brake_normal_servicex(V) is equal to the normal service brake model applicable for the concerned combination of brake position and of the value of A_brake_service(V=0) between dx-1 and dx (see 3.13.2.2.3.1.9 and 3.13.2.2.3.1.10).
- implement: true
- kind: ordinary
- CrossRefLink -> 3.13.2.2.3.1.9
- CrossRefLink -> 3.13.2.2.3.1.10

#### 3.13.7 (Requirement Type)
Determination of Most Restrictive Speed Profile (MRSP)
- WordTraceId: 176831
- atomic: false
- Legal Obligation: not applicable
- implement: false
- kind: Heading

##### 3.13.7.1 (Requirement Type)
The Most Restrictive Speed Profile (MRSP) is a description of the most restrictive speed restrictions the train shall obey on a given piece of track.
- WordTraceId: 176886
- atomic: true
- Legal Obligation: mandatory
- implement: true
- kind: ordinary

##### 3.13.7.2 (Requirement Type)
The Most Restrictive Speed Profile shall be computed from all speed restrictions (see 3.13.2.2.13 & 3.13.2.3.2) by selecting the most restrictive parts of each element, some elements being compensated by the train length if requested by trackside (see 3.11.3.1.3 for SSP, 3.11.4.6 for ASP and 3.11.5.3 for TSR).
- WordTraceId: 177036
- atomic: true
- Legal Obligation: mandatory
- implement: true
- implementerEnhanced: The Most Restrictive Speed Profile shall be computed from all speed restrictions (see 3.13.2.2.13 & 3.13.2.3.2) by selecting the most restrictive parts of each element, some elements being compensated by the train length
  if
  [CONDITION]
  requested by
  trackside
  [EXTERNAL]
  (see 3.11.3.1.3 for SSP, 3.11.4.6 for ASP and 3.11.5.3 for TSR).
- kind: ordinary
- CrossRefLink -> 3.13.2.2.13
- CrossRefLink -> 3.13.2.3.2
- CrossRefLink -> 3.11.3.1.3
- CrossRefLink -> 3.11.4.6
- CrossRefLink -> 3.11.5.3

##### 3.13.7.2[2] (Requirement Type)
- WordTraceId: 177493
- atomic: false
- Legal Obligation: not applicable
- implement: false
- kind: Placeholder

###### 3.13.7.2[2].[f]39 (Requirement Type)
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- WordTraceId: 177521
- atomic: false
- Legal Obligation: not applicable
- implement: false
- kind: Figure

###### 3.13.7.2[2].[f]39.C (Requirement Type)
Figure {Figure 39}: Most Restrictive Speed Profile selection
- WordTraceId: 177521
- atomic: true
- Legal Obligation: unknown
- PlainText: Figure 39: Most Restrictive Speed Profile selection
- implement: false
- kind: Figure

##### 3.13.7.3 (Requirement Type)
The Most Restrictive Speed Profile shall be recalculated when any of the elements it is built of is changed.
- WordTraceId: 177598
- atomic: true
- Legal Obligation: mandatory
- implement: true
- implementerEnhanced: The Most Restrictive Speed Profile shall be recalculated
  when
  [CONDITION]
  any of the elements it is built of is changed.
- kind: ordinary

#### 3.13.8 (Requirement Type)
Determination of targets and brake deceleration curves
- WordTraceId: 177707
- atomic: false
- Legal Obligation: not applicable
- implement: false
- kind: Heading

##### 3.13.8.1 (Requirement Type)
Introduction
- WordTraceId: 177762
- atomic: false
- Legal Obligation: not applicable
- implement: false
- kind: Heading

###### 3.13.8.1.1 (Requirement Type)
A target is defined by a target location and a target speed, to which the train must decelerate before reaching the target location.
- WordTraceId: 177775
- atomic: true
- Legal Obligation: unknown
- implement: true
- kind: ordinary

###### 3.13.8.1.2 (Requirement Type)
For that purpose, the on-board equipment shall use brake deceleration curves related to the supervised targets, from the deceleration values as specified in sections 3.13.6.2.1, 3.13.6.3.1and 3.13.6.4.
- WordTraceId: 177908
- atomic: true
- Legal Obligation: mandatory
- implement: true
- implementerEnhanced: For that purpose, the
  on-board equipment
  [SELF]
  shall use brake deceleration curves related to the supervised targets, from the deceleration values as specified in sections 3.13.6.2.1, 3.13.6.3.1and 3.13.6.4.
- kind: ordinary
- CrossRefLink -> 3.13.6.2.1
- CrossRefLink -> 3.13.6.3.1
- CrossRefLink -> 3.13.6.4

###### 3.13.8.1.3 (Requirement Type)
These deceleration values being speed and distance dependent, a brake deceleration curve shall be calculated piecewise, i.e. it shall be composed of interconnected arcs of parabola, each one being based on one of the speed/distance dependent deceleration values (see Figure 38).
- WordTraceId: 178244
- atomic: false
- Legal Obligation: mandatory
- implement: true
- kind: ordinary
- CrossRefLink -> 3.13.6.2.1.9[2].[f]38.C

##### 3.13.8.2 (Requirement Type)
Determination of the supervised targets
- WordTraceId: 178549
- atomic: false
- Legal Obligation: not applicable
- implement: false
- kind: Heading

###### 3.13.8.2.1 (Requirement Type)
The on-board shall continuously supervise a list of targets, which may include the following types of target:
- WordTraceId: 178589
- atomic: false
- Legal Obligation: mixed
- implement: true
- implementerEnhanced: The on-board shall
  continuously
  [WEAK]
  supervise a list of targets, which may include the following types of target:
- kind: ordinary

###### 3.13.8.2.1.a (Requirement Type)
the locations corresponding to a speed decrease of the MRSP (if any), which are in advance of the max safe front end of the train
- WordTraceId: 178699
- atomic: true
- Legal Obligation: unknown
- implement: true
- implementerEnhanced: the locations corresponding to a speed decrease of the MRSP (
  if
  [CONDITION]
  any), which are in advance of the max safe front end of the train
- ListNumberText: a)
- kind: ordinary

###### 3.13.8.2.1.b (Requirement Type)
the Limit of Authority (LOA), if the target speed at the EOA/LOA is not equal to zero
- WordTraceId: 178829
- atomic: true
- Legal Obligation: unknown
- implement: true
- implementerEnhanced: the Limit of Authority (LOA),
  if
  [CONDITION]
  the target speed at the EOA/LOA is not equal to zero
- ListNumberText: b)
- kind: ordinary

###### 3.13.8.2.1.c (Requirement Type)
the End of Authority (EOA) and the Supervised Location (SvL), if the target speed at the EOA is equal to zero
- WordTraceId: 178915
- atomic: true
- Legal Obligation: unknown
- implement: true
- implementerEnhanced: the End of Authority (EOA) and the Supervised Location (SvL),
  if
  [CONDITION]
  the target speed at the EOA is equal to zero
- ListNumberText: c)
- kind: ordinary

###### 3.13.8.2.1.d (Requirement Type)
the location deduced from the maximum permitted distance to run in Staff Responsible, with a target speed zero
- WordTraceId: 179025
- atomic: true
- Legal Obligation: unknown
- implement: true
- ListNumberText: d)
- kind: ordinary

###### 3.13.8.2.1.1 (Requirement Type)
Note: depending on the information received from trackside and the position of the train, the list of supervised targets may be empty.
- WordTraceId: 179136
- atomic: false
- Legal Obligation: optional
- implement: false
- implementerEnhanced: Note: depending on the information received from
  trackside
  [EXTERNAL]
  and the position of the train, the list of supervised targets may be empty.
- kind: Note

###### 3.13.8.2.2 (Requirement Type)
The list of supervised targets shall be re-evaluated when any of the elements it is built of is changed (e.g. new MA and/or track description accepted on-board, EOA and/or SvL temporarily supervised at the start location of a mode profile, update of stored information in specific situations (see sections A.3.4 and 4.10)).
- WordTraceId: 179271
- atomic: true
- Legal Obligation: mandatory
- implement: true
- implementerEnhanced: The list of supervised targets shall be
  re-evaluated
  [AGAIN]
  when
  [CONDITION]
  any of the elements it is built of is changed (
  e.g.
  [WEAK]
  new MA and/or track description accepted on-board, EOA and/or SvL
  temporarily
  [WEAK]
  supervised at the start location of a mode profile, update of stored information in specific situations (see sections A.3.4 and 4.10)).
- kind: ordinary
- CrossRefLink -> A.3.4
- CrossRefLink -> 4.10

###### 3.13.8.2.3 (Requirement Type)
A target corresponding to a speed decrease of the MRSP shall be removed from the list of supervised targets when the max safe front end of the train has passed the target location.
- WordTraceId: 179595
- atomic: true
- Legal Obligation: mandatory
- implement: true
- implementerEnhanced: A target corresponding to a speed decrease of the MRSP shall be removed from the list of supervised targets
  when
  [CONDITION]
  the max safe front end of the train has passed the target location.
- kind: ordinary

##### 3.13.8.3 (Requirement Type)
Emergency Brake Deceleration curves (EBD)
- WordTraceId: 179776
- atomic: false
- Legal Obligation: not applicable
- implement: false
- kind: Heading

###### 3.13.8.3.1 (Requirement Type)
If a target belongs to the MRSP or is an LOA, the on-board shall calculate an EBD curve based on the safe deceleration A_safe(V,d), that crosses the ceiling speed EBI supervision limit (see 3.13.9.2) at the target location, and that extends up to the location where the target speed is reached (EBD foot).
- WordTraceId: 179818
- atomic: true
- Legal Obligation: mandatory
- implement: true
- implementerEnhanced: If
  [CONDITION]
  a target belongs to the MRSP or is an LOA, the on-board shall calculate an EBD curve based on the safe deceleration A_safe(V,d), that crosses the ceiling speed EBI supervision limit (see 3.13.9.2) at the target location, and that extends up to the location where the target speed is reached (EBD foot).
- kind: ordinary
- CrossRefLink -> 3.13.9.2

###### 3.13.8.3.1[2] (Requirement Type)
- WordTraceId: 180169
- atomic: false
- Legal Obligation: not applicable
- implement: false
- kind: Placeholder

###### 3.13.8.3.1[2].[f]40 (Requirement Type)
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- WordTraceId: 180197
- atomic: false
- Legal Obligation: not applicable
- implement: false
- kind: Figure

###### 3.13.8.3.1[2].[f]40.C (Requirement Type)
Figure {Figure 40}: Calculation of the EBD curve with regards to MRSP or LOA target
- WordTraceId: 180197
- atomic: true
- Legal Obligation: unknown
- PlainText: Figure 40: Calculation of the EBD curve with regards to MRSP or LOA target
- implement: false
- kind: Figure

###### 3.13.8.3.2 (Requirement Type)
If a target is an SvL, the on-board shall calculate an Emergency Brake Deceleration (EBD) curve based on the safe deceleration A_safe(V,d) and that reaches zero speed at the SvL.
- WordTraceId: 180297
- atomic: true
- Legal Obligation: mandatory
- implement: true
- implementerEnhanced: If
  [CONDITION]
  a target is an SvL, the on-board shall calculate an Emergency Brake Deceleration (EBD) curve based on the safe deceleration A_safe(V,d) and that reaches zero speed at the SvL.
- kind: ordinary

###### 3.13.8.3.3 (Requirement Type)
If a target is the location at the end of the maximum permitted distance to run in Staff Responsible, the on-board shall calculate an Emergency Brake Deceleration (EBD) curve based on the safe deceleration A_safe(V,d) and that reaches zero speed at this staff responsible end location.
- WordTraceId: 180476
- atomic: true
- Legal Obligation: mandatory
- implement: true
- implementerEnhanced: If
  [CONDITION]
  a target is the location at the end of the maximum permitted distance to run in Staff Responsible, the on-board shall calculate an Emergency Brake Deceleration (EBD) curve based on the safe deceleration A_safe(V,d) and that reaches zero speed at this staff responsible end location.
- kind: ordinary

###### 3.13.8.3.3[2] (Requirement Type)
- WordTraceId: 180762
- atomic: false
- Legal Obligation: not applicable
- implement: false
- kind: Placeholder

###### 3.13.8.3.3[2].[f]41 (Requirement Type)
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- WordTraceId: 180790
- atomic: false
- Legal Obligation: not applicable
- implement: false
- kind: Figure

###### 3.13.8.3.3[2].[f]41.C (Requirement Type)
Figure {Figure 41}: Calculation of the EBD curve with regards to SvL or SR distance
- WordTraceId: 180790
- atomic: true
- Legal Obligation: unknown
- PlainText: Figure 41: Calculation of the EBD curve with regards to SvL or SR distance
- implement: false
- kind: Figure

##### 3.13.8.4 (Requirement Type)
Service Brake Deceleration curves (SBD)
- WordTraceId: 180890
- atomic: false
- Legal Obligation: not applicable
- implement: false
- kind: Heading

###### 3.13.8.4.1 (Requirement Type)
If a target is an EOA, the on-board shall calculate an Service Brake Deceleration (SBD) curve based on the expected deceleration A_expected(V,d) and that reaches zero speed at this EOA location.
- WordTraceId: 180930
- atomic: true
- Legal Obligation: mandatory
- implement: true
- implementerEnhanced: If
  [CONDITION]
  a target is an EOA, the on-board shall calculate an Service Brake Deceleration (SBD) curve based on the expected deceleration A_expected(V,d) and that reaches zero speed at this EOA location.
- kind: ordinary

###### 3.13.8.4.1[2] (Requirement Type)
- WordTraceId: 181125
- atomic: false
- Legal Obligation: not applicable
- implement: false
- kind: Placeholder

###### 3.13.8.4.1[2].[f]42 (Requirement Type)
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- WordTraceId: 181153
- atomic: false
- Legal Obligation: not applicable
- implement: false
- kind: Figure

###### 3.13.8.4.1[2].[f]42.C (Requirement Type)
Figure {Figure 42}: Calculation of the SBD curve with regards to EOA
- WordTraceId: 181153
- atomic: true
- Legal Obligation: unknown
- PlainText: Figure 42: Calculation of the SBD curve with regards to EOA
- implement: false
- kind: Figure

##### 3.13.8.5 (Requirement Type)
Guidance curves (GUI)
- WordTraceId: 181238
- atomic: false
- Legal Obligation: not applicable
- implement: false
- kind: Heading

###### 3.13.8.5.1 (Requirement Type)
The purpose of the guidance curve (GUI) is to provide a comfortable way of braking for the driver, to avoid excessive wear of the brakes and to save traction energy.
- WordTraceId: 181260
- atomic: true
- Legal Obligation: unknown
- implement: true
- implementerEnhanced: The purpose of the guidance curve (GUI) is to provide a comfortable way of braking for the
  driver
  [EXTERNAL]
  , to avoid excessive wear of the brakes and to save traction energy.
- kind: ordinary

###### 3.13.8.5.2 (Requirement Type)
If the National Value does not inhibit them, the on-board shall calculate a guidance curve (GUI) for each supervised target, based on the normal service brake deceleration A_normal_service(V,d). The foot of a GUI curve (i.e. the location where the GUI speed is equal to the target speed) shall be:
- WordTraceId: 181426
- atomic: false
- Legal Obligation: mandatory
- implement: true
- implementerEnhanced: If
  [CONDITION]
  the National Value does not inhibit them, the on-board shall calculate a guidance curve (GUI)
  for each
  [LOOP]
  supervised target, based on the normal service brake deceleration A_normal_service(V,d). The foot of a GUI curve (i.e. the location where the GUI speed is equal to the target speed) shall be:
- kind: ordinary

###### 3.13.8.5.2.a (Requirement Type)
the target location, in case of EOA/SvL
- WordTraceId: 181724
- atomic: true
- Legal Obligation: unknown
- implement: true
- implementerEnhanced: the target location,
  in case of
  [CONDITION]
  EOA/SvL
- ListNumberText: a)
- kind: ordinary

###### 3.13.8.5.2.b (Requirement Type)
the location defined in 3.13.9.3.5.9, for others targets
- WordTraceId: 181764
- atomic: true
- Legal Obligation: unknown
- implement: true
- ListNumberText: b)
- kind: ordinary
- CrossRefLink -> 3.13.9.3.5.9

#### 3.13.9 (Requirement Type)
Supervision limits
- WordTraceId: 181850
- atomic: false
- Legal Obligation: not applicable
- implement: false
- kind: Heading

##### 3.13.9.1 (Requirement Type)
Overview
- WordTraceId: 181869
- atomic: false
- Legal Obligation: not applicable
- implement: false
- kind: Heading

###### 3.13.9.1.1 (Requirement Type)
In this chapter the following supervision limits are defined:
- WordTraceId: 181878
- atomic: true
- Legal Obligation: unknown
- implement: false
- kind: Heading

###### 3.13.9.1.1.*[1] (Requirement Type)
Emergency brake intervention (EBI)
- WordTraceId: 181940
- atomic: true
- Legal Obligation: unknown
- implement: false
- ListNumberText: ·
- kind: Definition

###### 3.13.9.1.1.*[2] (Requirement Type)
Service brake intervention (SBI)
- WordTraceId: 181975
- atomic: true
- Legal Obligation: unknown
- implement: false
- ListNumberText: ·
- kind: Definition

###### 3.13.9.1.1.*[3] (Requirement Type)
Warning (W)
- WordTraceId: 182008
- atomic: true
- Legal Obligation: unknown
- implement: false
- ListNumberText: ·
- kind: Definition

###### 3.13.9.1.1.*[4] (Requirement Type)
Permitted speed (P)
- WordTraceId: 182020
- atomic: true
- Legal Obligation: unknown
- implement: false
- ListNumberText: ·
- kind: Definition

###### 3.13.9.1.1.*[5] (Requirement Type)
Indication (I)
- WordTraceId: 182040
- atomic: true
- Legal Obligation: unknown
- implement: false
- ListNumberText: ·
- kind: Definition

###### 3.13.9.1.1.*[6] (Requirement Type)
Pre-Indication location
- WordTraceId: 182055
- atomic: true
- Legal Obligation: unknown
- implement: false
- ListNumberText: ·
- kind: Definition

###### 3.13.9.1.1.*[7] (Requirement Type)
Release speed monitoring start location
- WordTraceId: 182079
- atomic: true
- Legal Obligation: unknown
- implement: false
- ListNumberText: ·
- kind: Definition

###### 3.13.9.1.2 (Requirement Type)
The purpose of the emergency brake intervention supervision limit is to assure that the train will remain within the various limits (in distance/speed) imposed by the trackside.
- WordTraceId: 182119
- atomic: true
- Legal Obligation: unknown
- implement: true
- implementerEnhanced: The purpose of the emergency brake intervention supervision limit is to assure that the train will remain within the various limits (in distance/speed) imposed by the
  trackside
  [EXTERNAL]
  .
- kind: ordinary

###### 3.13.9.1.3 (Requirement Type)
The purpose of all other supervision limits is to assist the driver in preventing an emergency brake intervention by maintaining the speed of the train within the appropriate limits.
- WordTraceId: 182297
- atomic: true
- Legal Obligation: unknown
- implement: true
- implementerEnhanced: The purpose of all other supervision limits is to assist the
  driver
  [EXTERNAL]
  in preventing an emergency brake intervention by maintaining the speed of the train within the appropriate limits.
- kind: ordinary

##### 3.13.9.2 (Requirement Type)
Ceiling supervision limits
- WordTraceId: 182480
- atomic: false
- Legal Obligation: not applicable
- implement: false
- kind: Heading

###### 3.13.9.2.1 (Requirement Type)
The ceiling supervision limits are derived from the MRSP elements, where the speed is constant (refer to 3.13.7) or from the LOA.
- WordTraceId: 182507
- atomic: true
- Legal Obligation: unknown
- implement: true
- kind: ordinary
- CrossRefLink -> 3.13.7

###### 3.13.9.2.2 (Requirement Type)
From an MRSP element or from the LOA, the Permitted speed, Warning, Service brake intervention and Emergency brake intervention supervision limits are defined (see Figure 43).
- WordTraceId: 182666
- atomic: true
- Legal Obligation: unknown
- implement: true
- kind: ordinary
- CrossRefLink -> 3.13.9.2.2[2].[f]43.C

###### 3.13.9.2.2[2] (Requirement Type)
- WordTraceId: 182868
- atomic: false
- Legal Obligation: not applicable
- implement: false
- kind: Placeholder

###### 3.13.9.2.2[2].[f]43 (Requirement Type)
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- WordTraceId: 182896
- atomic: false
- Legal Obligation: not applicable
- implement: false
- kind: Figure

###### 3.13.9.2.2[2].[f]43.C (Requirement Type)
Figure {Figure 43}: Ceiling supervision limits
- WordTraceId: 182896
- atomic: true
- Legal Obligation: unknown
- PlainText: Figure 43: Ceiling supervision limits
- implement: false
- implementerEnhanced: Figure 43: Ceiling supervision limits
- kind: Figure

###### 3.13.9.2.3 (Requirement Type)
For dv_ebi, the following formula shall be applied:
- WordTraceId: 182959
- atomic: true
- Legal Obligation: mandatory
- implement: true
- kind: ordinary

###### 3.13.9.2.3[2] (Requirement Type)
when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:
- WordTraceId: 183011
- atomic: true
- Legal Obligation: unknown
- PlainText: when :
- implement: true
- implementerEnhanced: when
  [CONDITION]
  :
- kind: ordinary

###### 3.13.9.2.3[3] (Requirement Type)
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- WordTraceId: 183041
- atomic: true
- Legal Obligation: unknown
- implement: true
- kind: ordinary

###### 3.13.9.2.3[4] (Requirement Type)
with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
- WordTraceId: 183065
- atomic: true
- Legal Obligation: unknown
- PlainText: with
- implement: true
- implementerEnhanced: with
- kind: ordinary

###### 3.13.9.2.3[5] (Requirement Type)
when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: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
- WordTraceId: 183094
- atomic: true
- Legal Obligation: unknown
- PlainText: when :
- implement: true
- implementerEnhanced: when
  [CONDITION]
  :
- kind: ordinary

###### 3.13.9.2.3[6] (Requirement Type)
- WordTraceId: 183148
- atomic: false
- Legal Obligation: not applicable
- implement: false
- kind: Placeholder

###### 3.13.9.2.3[6].[f]44 (Requirement Type)
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- WordTraceId: 183176
- atomic: false
- Legal Obligation: not applicable
- implement: false
- kind: Figure

###### 3.13.9.2.3[6].[f]44.C (Requirement Type)
Figure {Figure 44}: Definition of dV_ebi
- WordTraceId: 183176
- atomic: true
- Legal Obligation: unknown
- PlainText: Figure 44: Definition of dV_ebi
- implement: false
- implementerEnhanced: Figure 44: Definition of dV_ebi
- kind: Figure

###### 3.13.9.2.4 (Requirement Type)
dV_ebi_min, dV_ebi_max, V_ebi_min and V_ebi_max are defined as fixed values (See Appendix A3.1)
- WordTraceId: 183233
- atomic: true
- Legal Obligation: unknown
- implement: false
- kind: Definition
- CrossRefLink -> A.3.1

###### 3.13.9.2.5 (Requirement Type)
For dV_sbi, the same formula as for dV_ebi shall apply, dV_sbi_min, dV_sbi_max, V_sbi_min and V_sbi_max being also defined as fixed values (See Appendix A3.1)
- WordTraceId: 183329
- atomic: true
- Legal Obligation: mandatory
- implement: true
- kind: ordinary
- CrossRefLink -> A.3.1

###### 3.13.9.2.6 (Requirement Type)
For dV_warning, the same formula as for dV_ebi shall apply, dV_warning_min, dV_warning_max, V_warning_min and V_warning_max being also defined as fixed values (See Appendix A3.1)
- WordTraceId: 183488
- atomic: true
- Legal Obligation: mandatory
- implement: true
- kind: ordinary
- CrossRefLink -> A.3.1

###### 3.13.9.2.7 (Requirement Type)
For LOA, the same formulas shall apply, by substituting V_MRSP with V_LOA.
- WordTraceId: 183667
- atomic: true
- Legal Obligation: mandatory
- implement: true
- kind: ordinary

###### 3.13.9.2.8 (Requirement Type)
The SBI supervision limit is also referred as the FLOI (First Line Of Intervention) supervision limit.
- WordTraceId: 183742
- atomic: true
- Legal Obligation: unknown
- implement: true
- kind: ordinary

##### 3.13.9.3 (Requirement Type)
Braking to target supervision limits
- WordTraceId: 183845
- atomic: false
- Legal Obligation: not applicable
- implement: false
- kind: Heading

###### 3.13.9.3.1 (Requirement Type)
Overview
- WordTraceId: 183882
- atomic: false
- Legal Obligation: not applicable
- implement: false
- kind: Heading

###### 3.13.9.3.1.1 (Requirement Type)
The braking to target supervision limits are derived from the EBD, SBD and GUI curves.
- WordTraceId: 183891
- atomic: true
- Legal Obligation: unknown
- implement: true
- kind: ordinary

###### 3.13.9.3.1.2 (Requirement Type)
From an EBD curve, the Emergency brake intervention (EBI), Service brake intervention (SBI2), Warning (W), Permitted speed (P) and Indication (I) supervision limits, valid for the estimated speed, are defined as follows(see Figure 45):
- WordTraceId: 183978
- atomic: true
- Legal Obligation: unknown
- implement: false
- kind: Definition
- CrossRefLink -> 3.13.9.3.1.2[2].[f]45.C

###### 3.13.9.3.1.2[2] (Requirement Type)
- WordTraceId: 184240
- atomic: false
- Legal Obligation: not applicable
- implement: false
- kind: Placeholder

###### 3.13.9.3.1.2[2].[f]45 (Requirement Type)
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- WordTraceId: 184268
- atomic: false
- Legal Obligation: not applicable
- implement: false
- kind: Figure

###### 3.13.9.3.1.2[2].[f]45.C (Requirement Type)
Figure {Figure 45}: Braking to target supervision limits from EBD curve
- WordTraceId: 184268
- atomic: true
- Legal Obligation: unknown
- PlainText: Figure 45: Braking to target supervision limits from EBD curve
- implement: false
- kind: Figure

###### 3.13.9.3.1.3 (Requirement Type)
From the SBD curve, Service brake intervention (SBI1), Warning (W), Permitted speed (P) and Indication (I) supervision limits, valid for the estimated speed, are defined as follows (see Figure 46):
- WordTraceId: 184356
- atomic: true
- Legal Obligation: unknown
- implement: false
- kind: Definition
- CrossRefLink -> 3.13.9.3.1.3[2].[f]46.C

###### 3.13.9.3.1.3[2] (Requirement Type)
- WordTraceId: 184580
- atomic: false
- Legal Obligation: not applicable
- implement: false
- kind: Placeholder

###### 3.13.9.3.1.3[2].[f]46 (Requirement Type)
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- WordTraceId: 184608
- atomic: false
- Legal Obligation: not applicable
- implement: false
- kind: Figure

###### 3.13.9.3.1.3[2].[f]46.C (Requirement Type)
Figure {Figure 46}: Braking to target supervision limits from SBD curve
- WordTraceId: 184608
- atomic: true
- Legal Obligation: unknown
- PlainText: Figure 46: Braking to target supervision limits from SBD curve
- implement: false
- kind: Figure

###### 3.13.9.3.1.4 (Requirement Type)
No specific supervision limit is calculated from the GUI curve: it is only used to adjust the Permitted speed (P) supervision limit, which is obtained either from the EBD or the SBD curve.
- WordTraceId: 184696
- atomic: true
- Legal Obligation: unknown
- implement: true
- kind: ordinary

###### 3.13.9.3.2 (Requirement Type)
EBI supervision limit
- WordTraceId: 184885
- atomic: false
- Legal Obligation: not applicable
- implement: false
- kind: Heading

###### 3.13.9.3.2.1 (Requirement Type)
If not inhibited by National Value, the ERTMS/ETCS on-board equipment shall compensate the inaccuracy of the speed measurement by taking into account the speed under reading amount (V_ura) at the moment when the calculation is made: V_delta0 = V_ura (see Figure 45).
- WordTraceId: 184907
- atomic: true
- Legal Obligation: mandatory
- implement: true
- implementerEnhanced: If
  [CONDITION]
  not inhibited by National Value, the
  ERTMS/ETCS on-board equipment
  [SELF]
  shall compensate the inaccuracy of the speed measurement by taking into account the speed under reading amount (V_ura) at the moment
  when
  [CONDITION]
  the calculation is made: V_delta0 = V_ura (see Figure 45).
- kind: ordinary
- CrossRefLink -> 3.13.9.3.1.2[2].[f]45.C

###### 3.13.9.3.2.2 (Requirement Type)
The time elapsed between the Emergency brake intervention and the full application of the braking effort is reached (EBD) shall be split into two parts:
- WordTraceId: 185200
- atomic: true
- Legal Obligation: mandatory
- implement: true
- implementerEnhanced: The
  time
  [TIME]
  elapsed between the Emergency brake intervention and the full application of the braking effort is reached (EBD) shall be split into two parts:
- kind: ordinary

###### 3.13.9.3.2.2.a (Requirement Type)
Time during which the traction effort is still present: T_traction
- WordTraceId: 185353
- atomic: true
- Legal Obligation: unknown
- implement: true
- implementerEnhanced: Time
  [TIME]
  during
  [TIME]
  which the traction effort is still present: T_traction
- ListNumberText: a)
- kind: ordinary

###### 3.13.9.3.2.2.b (Requirement Type)
Remaining time during which the traction effort is not present: T_berem
- WordTraceId: 185420
- atomic: true
- Legal Obligation: unknown
- implement: true
- implementerEnhanced: Remaining
  time
  [TIME]
  during
  [TIME]
  which the traction effort is not present: T_berem
- ListNumberText: b)
- kind: ordinary

###### 3.13.9.3.2.3 (Requirement Type)
The traction time (T_Traction) shall be defined as follows:
- WordTraceId: 185492
- atomic: true
- Legal Obligation: mandatory
- implement: false
- implementerEnhanced: The traction
  time
  [TIME]
  (T_Traction) shall be defined as follows:
- kind: Definition

###### 3.13.9.3.2.3.a (Requirement Type)
when the traction cut-off is implemented:
- WordTraceId: 185552
- atomic: true
- Legal Obligation: unknown
- implement: false
- implementerEnhanced: when
  [CONDITION]
  the traction cut-off is implemented:
- ListNumberText: a)
- kind: Definition

###### 3.13.9.3.2.3.a[2] (Requirement Type)
T_traction = MAX((T_traction_cut_off - (T_warning + T_bs2)) ; 0).
- WordTraceId: 185594
- atomic: true
- Legal Obligation: unknown
- implement: false
- kind: Definition

###### 3.13.9.3.2.3.b (Requirement Type)
when the traction cut-off is not implemented: T_traction = T_traction_cut_off
- WordTraceId: 185660
- atomic: true
- Legal Obligation: unknown
- implement: false
- implementerEnhanced: when
  [CONDITION]
  the traction cut-off is not implemented: T_traction = T_traction_cut_off
- ListNumberText: b)
- kind: Definition

###### 3.13.9.3.2.4 (Requirement Type)
Note: When the traction cut-off is implemented, the traction cut-off command is triggered when passing the warning limit. The term (T_warning + T_bs2) in the equation above takes this into account, assuming that the warning limit is derived from the EBD.
- WordTraceId: 185738
- atomic: false
- Legal Obligation: not applicable
- implement: false
- implementerEnhanced: Note:
  When
  [CONDITION]
  the traction cut-off is implemented, the traction cut-off command is triggered
  when
  [CONDITION]
  passing the warning limit. The term (T_warning + T_bs2) in the equation
  above
  [WEAK]
  takes this into account, assuming that the warning limit is derived from the EBD.
- kind: Note

###### 3.13.9.3.2.5 (Requirement Type)
T_bs2 and T_warning are defined in sections 3.13.9.3.3 and 3.13.9.3.4.
- WordTraceId: 185993
- atomic: true
- Legal Obligation: unknown
- implement: true
- kind: ordinary
- CrossRefLink -> 3.13.9.3.3
- CrossRefLink -> 3.13.9.3.4

###### 3.13.9.3.2.6 (Requirement Type)
The remaining time with no traction (T_berem) shall be equal to MAX(T_be - T_traction ; 0).
- WordTraceId: 186122
- atomic: true
- Legal Obligation: mandatory
- implement: true
- implementerEnhanced: The remaining
  time
  [TIME]
  with no traction (T_berem) shall be equal to MAX(T_be - T_traction ; 0).
- kind: ordinary

###### 3.13.9.3.2.7 (Requirement Type)
Note: T_Traction exceeding T_be is rather a theoretical case, but is nevertheless included to make the specifications complete.
- WordTraceId: 186214
- atomic: false
- Legal Obligation: not applicable
- implement: false
- kind: Note

###### 3.13.9.3.2.8 (Requirement Type)
During T_traction, the estimated acceleration/deceleration (A_est1), which is measured at the moment when the calculation is made, shall be taken into account.
- WordTraceId: 186342
- atomic: true
- Legal Obligation: mandatory
- implement: true
- implementerEnhanced: During
  [TIME]
  T_traction, the estimated acceleration/deceleration (A_est1), which is measured at the moment
  when
  [CONDITION]
  the calculation is made, shall be taken into account.
- kind: ordinary

###### 3.13.9.3.2.9 (Requirement Type)
If T_be > T_traction, the estimated acceleration during T_berem (A_est2) shall be the one measured at the moment when the calculation is made, but limited to values between 0 and +0.4m/s
2
.
- WordTraceId: 186502
- atomic: true
- Legal Obligation: mandatory
- PlainText: If T_be > T_traction, the estimated acceleration during T_berem (A_est2) shall be the one measured at the moment when the calculation is made, but limited to values between 0 and +0.4m/s2.
- implement: true
- implementerEnhanced: If
  [CONDITION]
  T_be > T_traction, the estimated acceleration
  during
  [TIME]
  T_berem (A_est2) shall be the one measured at the moment
  when
  [CONDITION]
  the calculation is made, but limited to values between 0 and +0.4m/s2.
- kind: ordinary

###### 3.13.9.3.2.10 (Requirement Type)
The compensated speed and the distance travelled during the time elapsed between the Emergency brake intervention and the full application of the braking effort is reached shall be derived as follows (see Figure 45):
- WordTraceId: 186691
- atomic: true
- Legal Obligation: mandatory
- implement: true
- implementerEnhanced: The compensated speed and the distance travelled
  during
  [TIME]
  the
  time
  [TIME]
  elapsed between the Emergency brake intervention and the full application of the braking effort is reached shall be derived as follows (see Figure 45):
- kind: ordinary
- CrossRefLink -> 3.13.9.3.1.2[2].[f]45.C

###### 3.13.9.3.2.10[2] (Requirement Type)
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- WordTraceId: 186934
- atomic: true
- Legal Obligation: unknown
- implement: true
- kind: ordinary

###### 3.13.9.3.2.10[3] (Requirement Type)
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- WordTraceId: 186958
- atomic: true
- Legal Obligation: unknown
- implement: true
- kind: ordinary

###### 3.13.9.3.2.10[4] (Requirement Type)
with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 or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 (if compensation of speed inaccuracy is inhibited by National Value)
- WordTraceId: 186982
- atomic: true
- Legal Obligation: unknown
- PlainText: with  or  (if compensation of speed inaccuracy is inhibited by National Value)
- implement: true
- implementerEnhanced: with or (
  if
  [CONDITION]
  compensation of speed inaccuracy is inhibited by National Value)
- kind: ordinary

###### 3.13.9.3.2.10[5] (Requirement Type)
with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 and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
- WordTraceId: 187107
- atomic: true
- Legal Obligation: unknown
- PlainText: with  and
- implement: true
- implementerEnhanced: with and
- kind: ordinary

###### 3.13.9.3.2.11 (Requirement Type)
Note: The formula avoids that, in case A_est1 < 0, V_bec would become lower than V_target.
- WordTraceId: 187164
- atomic: false
- Legal Obligation: not applicable
- implement: false
- implementerEnhanced: Note: The formula avoids that,
  in case
  [CONDITION]
  A_est1 < 0, V_bec would become lower than V_target.
- kind: Note

###### 3.13.9.3.2.12 (Requirement Type)
For the estimated speed V_est, the location of the EBI supervision limit shall be:
- WordTraceId: 187255
- atomic: true
- Legal Obligation: mandatory
- implement: true
- kind: ordinary

###### 3.13.9.3.2.12[2] (Requirement Type)
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- WordTraceId: 187338
- atomic: true
- Legal Obligation: unknown
- implement: true
- kind: ordinary

###### 3.13.9.3.3 (Requirement Type)
SBI supervision limit
- WordTraceId: 187362
- atomic: false
- Legal Obligation: not applicable
- implement: false
- kind: Heading

###### 3.13.9.3.3.1 (Requirement Type)
For the EOA, the on-board shall calculate the location of the SBI supervision limit (SBI1) valid for the estimated speed, assuming that this latter remains constant during the interval T_bs1, until the SBD curve is reached.
- WordTraceId: 187384
- atomic: true
- Legal Obligation: mandatory
- implement: true
- implementerEnhanced: For the EOA, the on-board shall calculate the location of the SBI supervision limit (SBI1) valid for the estimated speed, assuming that this latter remains constant
  during
  [TIME]
  the interval T_bs1,
  until
  [TIME]
  the SBD curve is reached.
- kind: ordinary

###### 3.13.9.3.3.1[2] (Requirement Type)
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- WordTraceId: 187608
- atomic: true
- Legal Obligation: unknown
- implement: true
- kind: ordinary

###### 3.13.9.3.3.2 (Requirement Type)
For an EBD based target, the on-board shall calculate the location of the SBI supervision limit (SBI2) valid for the estimated speed, assuming that this latter remains constant during the interval T_bs2, until the location of the EBI supervision limit is reached.
- WordTraceId: 187632
- atomic: true
- Legal Obligation: mandatory
- implement: true
- implementerEnhanced: For an EBD based target, the on-board shall calculate the location of the SBI supervision limit (SBI2) valid for the estimated speed, assuming that this latter remains constant
  during
  [TIME]
  the interval T_bs2,
  until
  [TIME]
  the location of the EBI supervision limit is reached.
- kind: ordinary

###### 3.13.9.3.3.2[2] (Requirement Type)
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- WordTraceId: 187896
- atomic: true
- Legal Obligation: unknown
- implement: true
- kind: ordinary

###### 3.13.9.3.3.3 (Requirement Type)
If the service brake command is available for use and the service brake feedback is not available for use, T_bs1 and T_bs2 shall be equal to T_bs.
- WordTraceId: 187920
- atomic: true
- Legal Obligation: mandatory
- implement: true
- implementerEnhanced: If
  [CONDITION]
  the service brake command is available for use and the service brake feedback is not available for use, T_bs1 and T_bs2 shall be equal to T_bs.
- kind: ordinary

###### 3.13.9.3.3.4 (Requirement Type)
If both the service brake command and the service brake feedback are available for use, T_bs1 and T_bs2 shall be firstly set to T_bs. When the service brake is used by the driver, they shall then be reduced progressively and possibly locked to the respective fixed values of 0s and T_bs2_locked, until the target location is passed or until the target speed monitoring is left; they are then reset again to T_bs (see detailed algorithm in Appendix A3.10).
- WordTraceId: 188067
- atomic: false
- Legal Obligation: mandatory
- implement: true
- implementerEnhanced: If
  [CONDITION]
  both the service brake command and the service brake feedback are available for use, T_bs1 and T_bs2 shall be firstly set to T_bs.
  When
  [CONDITION]
  the service brake is used by the
  driver
  [EXTERNAL]
  , they shall then be reduced progressively and
  possibly
  [WEAK]
  locked to the respective fixed values of 0s and T_bs2_locked,
  until
  [TIME]
  the target location is passed or
  until
  [TIME]
  the target speed monitoring is left; they are then reset
  again
  [LOOP]
  to T_bs (see detailed algorithm in Appendix A3.10).
- kind: ordinary
- CrossRefLink -> A.3.10

###### 3.13.9.3.3.4.1 (Requirement Type)
In case T_bs < T_bs2_locked then T_bs2 shall be equal to T_bs2_locked.
- WordTraceId: 188523
- atomic: true
- Legal Obligation: mandatory
- implement: true
- implementerEnhanced: In case
  [CONDITION]
  T_bs < T_bs2_locked then T_bs2 shall be equal to T_bs2_locked.
- kind: ordinary

###### 3.13.9.3.3.5 (Requirement Type)
If the service brake command is not available for use, T_bs1 and T_bs2 shall be set to zero.
- WordTraceId: 188594
- atomic: true
- Legal Obligation: mandatory
- implement: true
- implementerEnhanced: If
  [CONDITION]
  the service brake command is not available for use, T_bs1 and T_bs2 shall be set to zero.
- kind: ordinary

###### 3.13.9.3.3.6 (Requirement Type)
Note: The values T_bs1 and T_bs2 = 0s are defined to achieve the maximum performance when service brake command is not used.
- WordTraceId: 188687
- atomic: false
- Legal Obligation: not applicable
- implement: false
- implementerEnhanced: Note: The values T_bs1 and T_bs2 = 0s are defined to achieve the maximum performance
  when
  [CONDITION]
  service brake command is not used.
- kind: Note

###### 3.13.9.3.3.7 (Requirement Type)
For display purpose only, the SBI1 speed for the estimated train front end, shall be calculated as follows (see Figure 47):
- WordTraceId: 188812
- atomic: true
- Legal Obligation: mandatory
- implement: true
- kind: ordinary
- CrossRefLink -> 3.13.9.3.3.7[4].[f]47.C

###### 3.13.9.3.3.7[2] (Requirement Type)
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- WordTraceId: 188962
- atomic: true
- Legal Obligation: unknown
- implement: true
- kind: ordinary

###### 3.13.9.3.3.7[3] (Requirement Type)
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 if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
- WordTraceId: 188986
- atomic: true
- Legal Obligation: unknown
- PlainText: if
- implement: true
- implementerEnhanced: if
  [CONDITION]
- kind: ordinary

###### 3.13.9.3.3.7[4] (Requirement Type)
- WordTraceId: 189037
- atomic: false
- Legal Obligation: not applicable
- implement: false
- kind: Placeholder

###### 3.13.9.3.3.7[4].[f]47 (Requirement Type)
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- WordTraceId: 189065
- atomic: false
- Legal Obligation: not applicable
- implement: false
- kind: Figure

###### 3.13.9.3.3.7[4].[f]47.C (Requirement Type)
Figure {Figure 47}: Calculation of SBI1 speed displayed to the driver
- WordTraceId: 189065
- atomic: true
- Legal Obligation: unknown
- PlainText: Figure 47: Calculation of SBI1 speed displayed to the driver
- implement: false
- implementerEnhanced: Figure 47: Calculation of SBI1 speed displayed to the
  driver
  [EXTERNAL]
- kind: Figure

###### 3.13.9.3.3.8 (Requirement Type)
For display purpose only, the SBI2 speed for the max safe front end of the train shall be calculated as follows (see Figure 48):
- WordTraceId: 189151
- atomic: true
- Legal Obligation: mandatory
- implement: true
- kind: ordinary
- CrossRefLink -> 3.13.9.3.3.8[5].[f]48.C

###### 3.13.9.3.3.8[2] (Requirement Type)
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- WordTraceId: 189306
- atomic: true
- Legal Obligation: unknown
- implement: true
- kind: ordinary

###### 3.13.9.3.3.8[3] (Requirement Type)
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 if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
- WordTraceId: 189330
- atomic: true
- Legal Obligation: unknown
- PlainText: if
- implement: true
- implementerEnhanced: if
  [CONDITION]
- kind: ordinary

###### 3.13.9.3.3.8[4] (Requirement Type)
With D_bec and V_bec calculated according to 3.13.9.3.2.10
- WordTraceId: 189381
- atomic: true
- Legal Obligation: unknown
- implement: true
- kind: ordinary
- CrossRefLink -> 3.13.9.3.2.10

###### 3.13.9.3.3.8[5] (Requirement Type)
- WordTraceId: 189469
- atomic: false
- Legal Obligation: not applicable
- implement: false
- kind: Placeholder

###### 3.13.9.3.3.8[5].[f]48 (Requirement Type)
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- WordTraceId: 189497
- atomic: false
- Legal Obligation: not applicable
- implement: false
- kind: Figure

###### 3.13.9.3.3.8[5].[f]48.C (Requirement Type)
Figure {Figure 48}: Calculation of SBI2 speed displayed to the driver
- WordTraceId: 189497
- atomic: true
- Legal Obligation: unknown
- PlainText: Figure 48: Calculation of SBI2 speed displayed to the driver
- implement: false
- implementerEnhanced: Figure 48: Calculation of SBI2 speed displayed to the
  driver
  [EXTERNAL]
- kind: Figure

###### 3.13.9.3.3.8[5].1 (Requirement Type)
Note: the re-use of the same distance travelled and speed increase between the SBI2 supervision limit and the EBD, as for the estimated speed (see Figure 48), leads to an overestimation/underestimation of the SBI2 speed to be displayed to the driver. This simplification, which avoids the need of an iterated calculation, is however acceptable and necessary since the error made tends to zero when the train reaches the SBI2 supervision limit.
- WordTraceId: 189583
- atomic: false
- Legal Obligation: not applicable
- implement: false
- implementerEnhanced: Note: the
  re-use
  [AGAIN]
  of the same distance travelled and speed increase between the SBI2 supervision limit and the EBD, as for the estimated speed (see Figure 48), leads to an overestimation/underestimation of the SBI2 speed to be displayed to the
  driver
  [EXTERNAL]
  . This simplification, which avoids the need of an iterated calculation, is however acceptable and necessary since the error made
  tends to
  [WEAK]
  zero
  when
  [CONDITION]
  the train reaches the SBI2 supervision limit.
- ListNumberText: 3.13.9.3.3.8.1
- kind: Note
- CrossRefLink -> 3.13.9.3.3.8[5].[f]48.C

###### 3.13.9.3.3.9 (Requirement Type)
The FLOI (First Line Of Intervention) supervision limit, valid for estimated speed, shall be defined as the SBI supervision limit, of which the location is the closest to the train front, taking into account the max safe train front end for the SBI2 supervision limit(s) and the estimated train front end for the SBI1.
- WordTraceId: 190053
- atomic: true
- Legal Obligation: mandatory
- implement: false
- kind: Definition

###### 3.13.9.3.3.9[2] (Requirement Type)
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 if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
- WordTraceId: 190372
- atomic: true
- Legal Obligation: unknown
- PlainText: if
- implement: true
- implementerEnhanced: if
  [CONDITION]
- kind: ordinary

###### 3.13.9.3.3.9[3] (Requirement Type)
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 if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
- WordTraceId: 190423
- atomic: true
- Legal Obligation: unknown
- PlainText: if
- implement: true
- implementerEnhanced: if
  [CONDITION]
- kind: ordinary

###### 3.13.9.3.3.9[4] (Requirement Type)
With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
- WordTraceId: 190474
- atomic: true
- Legal Obligation: unknown
- PlainText: With
- implement: true
- implementerEnhanced: With
- kind: ordinary

###### 3.13.9.3.3.9[5] (Requirement Type)
MREBDT = Most Restrictive Target amongst the EBD based targets
- WordTraceId: 190503
- atomic: true
- Legal Obligation: unknown
- implement: true
- kind: ordinary

###### 3.13.9.3.4 (Requirement Type)
Warning supervision limit (W)
- WordTraceId: 190566
- atomic: false
- Legal Obligation: not applicable
- implement: false
- kind: Heading

###### 3.13.9.3.4.1 (Requirement Type)
The on-board shall calculate the location of the Warning supervision limit valid for the estimated speed, assuming that this latter remains constant during the interval T_warning until the location of the FLOI supervision limit is reached.
- WordTraceId: 190596
- atomic: true
- Legal Obligation: mandatory
- implement: true
- implementerEnhanced: The on-board shall calculate the location of the Warning supervision limit valid for the estimated speed, assuming that this latter remains constant
  during
  [TIME]
  the interval T_warning
  until
  [TIME]
  the location of the FLOI supervision limit is reached.
- kind: ordinary

###### 3.13.9.3.4.1[2] (Requirement Type)
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- WordTraceId: 190836
- atomic: true
- Legal Obligation: unknown
- implement: true
- kind: ordinary

###### 3.13.9.3.4.2 (Requirement Type)
T_warning is defined as a fixed value (refer to A3.1).
- WordTraceId: 190860
- atomic: true
- Legal Obligation: unknown
- implement: false
- kind: Definition
- CrossRefLink -> A.3.1

###### 3.13.9.3.5 (Requirement Type)
Permitted speed supervision limit (P)
- WordTraceId: 190915
- atomic: false
- Legal Obligation: not applicable
- implement: false
- kind: Heading

###### 3.13.9.3.5.1 (Requirement Type)
In case the calculation of the GUI curve is inhibited, the on-board shall calculate the location of the Permitted speed supervision limit valid for the estimated speed, assuming that this latter remains constant during the interval T_driver until the location of the FLOI supervision limit is reached.
- WordTraceId: 190953
- atomic: true
- Legal Obligation: mandatory
- implement: true
- implementerEnhanced: In case
  [CONDITION]
  the calculation of the GUI curve is inhibited, the on-board shall calculate the location of the Permitted speed supervision limit valid for the estimated speed, assuming that this latter remains constant
  during
  [TIME]
  the interval T_driver
  until
  [TIME]
  the location of the FLOI supervision limit is reached.
- kind: ordinary

###### 3.13.9.3.5.1[2] (Requirement Type)
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- WordTraceId: 191255
- atomic: true
- Legal Obligation: unknown
- implement: true
- kind: ordinary

###### 3.13.9.3.5.2 (Requirement Type)
T_driver is defined as a fixed value (refer to A3.1).
- WordTraceId: 191279
- atomic: true
- Legal Obligation: unknown
- implement: false
- kind: Definition
- CrossRefLink -> A.3.1

###### 3.13.9.3.5.3 (Requirement Type)
Note: The reference for the Permitted speed supervision limit is the FLOI supervision limit and not the Warning supervision limit. As a result the permitted and warning supervision limits are clearly separated and do not affect each other. In this way it is clear that the warning is not part of the critical performance interval.
- WordTraceId: 191333
- atomic: false
- Legal Obligation: not applicable
- implement: false
- implementerEnhanced: Note: The reference for the Permitted speed supervision limit is the FLOI supervision limit and not the Warning supervision limit. As a result the permitted and warning supervision limits are clearly separated and do not affect each other. In this way it is
  clear
  [WEAK]
  that the warning is not part of the critical performance interval.
- kind: Note

###### 3.13.9.3.5.4 (Requirement Type)
In case the calculation of the Guidance curve is enabled, the on-board shall calculate the location of the Permitted speed supervision limit valid for the estimated speed, as follows:
- WordTraceId: 191664
- atomic: true
- Legal Obligation: mandatory
- implement: true
- implementerEnhanced: In case
  [CONDITION]
  the calculation of the Guidance curve is enabled, the on-board shall calculate the location of the Permitted speed supervision limit valid for the estimated speed, as follows:
- kind: ordinary

###### 3.13.9.3.5.4[2] (Requirement Type)
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- WordTraceId: 191848
- atomic: true
- Legal Obligation: unknown
- implement: true
- kind: ordinary

###### 3.13.9.3.5.5 (Requirement Type)
In case the calculation of the GUI curve is inhibited, for display purpose only, the P speed related to SBD shall be calculated for the estimated train front end as follows:
- WordTraceId: 191872
- atomic: true
- Legal Obligation: mandatory
- implement: true
- implementerEnhanced: In case
  [CONDITION]
  the calculation of the GUI curve is inhibited, for display purpose only, the P speed related to SBD shall be calculated for the estimated train front end as follows:
- kind: ordinary

###### 3.13.9.3.5.5[2] (Requirement Type)
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- WordTraceId: 192046
- atomic: true
- Legal Obligation: unknown
- implement: true
- kind: ordinary

###### 3.13.9.3.5.5[3] (Requirement Type)
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 if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
- WordTraceId: 192070
- atomic: true
- Legal Obligation: unknown
- PlainText: if
- implement: true
- implementerEnhanced: if
  [CONDITION]
- kind: ordinary

###### 3.13.9.3.5.6 (Requirement Type)
In case the calculation of the GUI curve is enabled, for display purpose only, the P speed related to SBD shall be calculated for the estimated train front end as follows:
- WordTraceId: 192121
- atomic: true
- Legal Obligation: mandatory
- implement: true
- implementerEnhanced: In case
  [CONDITION]
  the calculation of the GUI curve is enabled, for display purpose only, the P speed related to SBD shall be calculated for the estimated train front end as follows:
- kind: ordinary

###### 3.13.9.3.5.6[2] (Requirement Type)
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- WordTraceId: 192293
- atomic: true
- Legal Obligation: unknown
- implement: true
- kind: ordinary

###### 3.13.9.3.5.6[3] (Requirement Type)
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 if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
- WordTraceId: 192317
- atomic: true
- Legal Obligation: unknown
- PlainText: if
- implement: true
- implementerEnhanced: if
  [CONDITION]
- kind: ordinary

###### 3.13.9.3.5.7 (Requirement Type)
In case the calculation of the GUI curve is inhibited, for display purpose only, the P speed related to EBD, shall be calculated for the max safe front end of the train as follows (see Figure 49):
- WordTraceId: 192368
- atomic: true
- Legal Obligation: mandatory
- implement: true
- implementerEnhanced: In case
  [CONDITION]
  the calculation of the GUI curve is inhibited, for display purpose only, the P speed related to EBD, shall be calculated for the max safe front end of the train as follows (see Figure 49):
- kind: ordinary
- CrossRefLink -> 3.13.9.3.5.7[5].[f]49.C

###### 3.13.9.3.5.7[2] (Requirement Type)
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- WordTraceId: 192591
- atomic: true
- Legal Obligation: unknown
- implement: true
- kind: ordinary

###### 3.13.9.3.5.7[3] (Requirement Type)
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 if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
- WordTraceId: 192615
- atomic: true
- Legal Obligation: unknown
- PlainText: if
- implement: true
- implementerEnhanced: if
  [CONDITION]
- kind: ordinary

###### 3.13.9.3.5.7[4] (Requirement Type)
With D_bec and V_bec calculated according to 3.13.9.3.2.10
- WordTraceId: 192666
- atomic: true
- Legal Obligation: unknown
- implement: true
- kind: ordinary
- CrossRefLink -> 3.13.9.3.2.10

###### 3.13.9.3.5.7[5] (Requirement Type)
- WordTraceId: 192754
- atomic: false
- Legal Obligation: not applicable
- implement: false
- kind: Placeholder

###### 3.13.9.3.5.7[5].[f]49 (Requirement Type)
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- WordTraceId: 192782
- atomic: false
- Legal Obligation: not applicable
- implement: false
- kind: Figure

###### 3.13.9.3.5.7[5].[f]49.C (Requirement Type)
Figure {Figure 49}: Calculation of Permitted speed displayed to the driver
- WordTraceId: 192782
- atomic: true
- Legal Obligation: unknown
- PlainText: Figure 49: Calculation of Permitted speed displayed to the driver
- implement: false
- implementerEnhanced: Figure 49: Calculation of Permitted speed displayed to the
  driver
  [EXTERNAL]
- kind: Figure

###### 3.13.9.3.5.7[5].1 (Requirement Type)
Note: the re-use of the same distance travelled and speed increase between the Permitted speed supervision limit and the EBD, as for the estimated speed (see Figure 49), leads to an overestimation/underestimation of the Permitted speed to be displayed to the driver. This simplification, which avoids the need of an iterated calculation, is however acceptable and necessary since the error made tends to zero when the train reaches the Permitted speed supervision limit.
- WordTraceId: 192873
- atomic: false
- Legal Obligation: not applicable
- implement: false
- implementerEnhanced: Note: the
  re-use
  [AGAIN]
  of the same distance travelled and speed increase between the Permitted speed supervision limit and the EBD, as for the estimated speed (see Figure 49), leads to an overestimation/underestimation of the Permitted speed to be displayed to the
  driver
  [EXTERNAL]
  . This simplification, which avoids the need of an iterated calculation, is however acceptable and necessary since the error made
  tends to
  [WEAK]
  zero
  when
  [CONDITION]
  the train reaches the Permitted speed supervision limit.
- ListNumberText: 3.13.9.3.5.7.1
- kind: Note
- CrossRefLink -> 3.13.9.3.5.7[5].[f]49.C

###### 3.13.9.3.5.8 (Requirement Type)
In case the calculation of the GUI curve is enabled, for display purpose only, the P speed related to EBD, shall be calculated for the max safe front end of the train as follows:
- WordTraceId: 193370
- atomic: true
- Legal Obligation: mandatory
- implement: true
- implementerEnhanced: In case
  [CONDITION]
  the calculation of the GUI curve is enabled, for display purpose only, the P speed related to EBD, shall be calculated for the max safe front end of the train as follows:
- kind: ordinary

###### 3.13.9.3.5.8[2] (Requirement Type)
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- WordTraceId: 193549
- atomic: true
- Legal Obligation: unknown
- implement: true
- kind: ordinary

###### 3.13.9.3.5.8[3] (Requirement Type)
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 if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
- WordTraceId: 193573
- atomic: true
- Legal Obligation: unknown
- PlainText: if
- implement: true
- implementerEnhanced: if
  [CONDITION]
- kind: ordinary

###### 3.13.9.3.5.8[4] (Requirement Type)
or if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
- WordTraceId: 193624
- atomic: true
- Legal Obligation: unknown
- PlainText: or if
- implement: true
- implementerEnhanced: or
  if
  [CONDITION]
- kind: ordinary

###### 3.13.9.3.5.8[5] (Requirement Type)
With D_bec and V_bec calculated according to 3.13.9.3.2.10
- WordTraceId: 193654
- atomic: true
- Legal Obligation: unknown
- implement: true
- kind: ordinary
- CrossRefLink -> 3.13.9.3.2.10

###### 3.13.9.3.5.9 (Requirement Type)
In order to determine the reference location of the target distance displayed to the driver and in order to determine the foot of the GUI curve (only if it is enabled) in case of target different from EOA/SvL, the location of the Permitted speed supervision limit, valid for the target speed, shall be calculated from the EBD, taking into account the following assumptions:
- WordTraceId: 193742
- atomic: true
- Legal Obligation: mandatory
- implement: true
- implementerEnhanced: In order to determine the reference location of the target distance displayed to the
  driver
  [EXTERNAL]
  and in order to determine the foot of the GUI curve (only
  if
  [CONDITION]
  it is enabled)
  in case of
  [CONDITION]
  target different from EOA/SvL, the location of the Permitted speed supervision limit, valid for the target speed, shall be calculated from the EBD, taking into account the following assumptions:
- kind: ordinary

###### 3.13.9.3.5.9.a (Requirement Type)
the estimated acceleration shall be set to “zero”
- WordTraceId: 194116
- atomic: true
- Legal Obligation: mandatory
- implement: true
- ListNumberText: a)
- kind: ordinary

###### 3.13.9.3.5.9.b (Requirement Type)
if not inhibited by National Value, the compensation of the inaccuracy of the speed measurement shall be set to a value calculated from the target speed, as defined in SUBSET-041 § 5.3.1.2: V_delta0t = f
41
(V_target)
- WordTraceId: 194166
- atomic: true
- Legal Obligation: mandatory
- PlainText: if not inhibited by National Value, the compensation of the inaccuracy of the speed measurement shall be set to a value calculated from the target speed, as defined in SUBSET-041 § 5.3.1.2: V_delta0t = f41(V_target)
- implement: true
- implementerEnhanced: if
  [CONDITION]
  not inhibited by National Value, the compensation of the inaccuracy of the speed measurement shall be set to a value calculated from the target speed, as defined in SUBSET-041 § 5.3.1.2: V_delta0t = f41(V_target)
- ListNumberText: b)
- kind: ordinary

###### 3.13.9.3.5.10 (Requirement Type)
To do so, the same formulas defined above with V_est and V_delta0 shall be applied, by substituting V_est with V_target and V_delta0 with V_delta0t.
- WordTraceId: 194382
- atomic: true
- Legal Obligation: mandatory
- implement: true
- implementerEnhanced: To do so, the same formulas defined
  above
  [WEAK]
  with V_est and V_delta0 shall be applied, by substituting V_est with V_target and V_delta0 with V_delta0t.
- kind: ordinary

###### 3.13.9.3.5.10[2] (Requirement Type)
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- WordTraceId: 194531
- atomic: true
- Legal Obligation: unknown
- implement: true
- kind: ordinary

###### 3.13.9.3.5.10[3] (Requirement Type)
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- WordTraceId: 194555
- atomic: true
- Legal Obligation: unknown
- implement: true
- kind: ordinary

###### 3.13.9.3.5.10[3].1 (Requirement Type)
Justification: these assumptions are intended to avoid fluctuations of the target distance displayed to the driver. Moreover the foot of the GUI curve may influence the pre-indication location, which must be fully predictable for trackside engineering reasons.
- WordTraceId: 194579
- atomic: false
- Legal Obligation: optional
- implement: false
- implementerEnhanced: Justification: these assumptions are intended to avoid fluctuations of the target distance displayed to the
  driver
  [EXTERNAL]
  . Moreover the foot of the GUI curve may influence the pre-indication location, which must be fully predictable for
  trackside
  [EXTERNAL]
  engineering reasons.
- ListNumberText: 3.13.9.3.5.10.1
- kind: Justification

###### 3.13.9.3.5.11 (Requirement Type)
In case a non protected LX start location is supervised as both the EOA and SvL and the stopping in rear of LX is not required, the location of the Permitted speed supervision limit, valid for the LX speed shall be used in order to determine the location where the supervision of the LX start location is substituted by the supervision of the LX speed (see section 5.16.3). This location shall be calculated taking into account the following assumptions:
- WordTraceId: 194840
- atomic: false
- Legal Obligation: not applicable
- implement: false
- implementerEnhanced: In case
  [CONDITION]
  a non protected LX start location is supervised as both the EOA and SvL and the stopping in rear of LX is not required, the location of the Permitted speed supervision limit, valid for the LX speed shall be used in order to determine the location where the supervision of the LX start location is substituted by the supervision of the LX speed (see section 5.16.3). This location shall be calculated taking into account the following assumptions:
- kind: Heading
- CrossRefLink -> 5.16.3

###### 3.13.9.3.5.11.a (Requirement Type)
the estimated acceleration shall be set to “zero”
- WordTraceId: 195295
- atomic: true
- Legal Obligation: mandatory
- implement: true
- ListNumberText: a)
- kind: ordinary

###### 3.13.9.3.5.11.b (Requirement Type)
if not inhibited by National Value, the compensation of the inaccuracy of the speed measurement shall be set to a value calculated from the LX speed, as defined in SUBSET-041 § 5.3.1.2: V_delta0lx = f
41
(V_LX)
- WordTraceId: 195345
- atomic: true
- Legal Obligation: mandatory
- PlainText: if not inhibited by National Value, the compensation of the inaccuracy of the speed measurement shall be set to a value calculated from the LX speed, as defined in SUBSET-041 § 5.3.1.2: V_delta0lx = f41(V_LX)
- implement: true
- implementerEnhanced: if
  [CONDITION]
  not inhibited by National Value, the compensation of the inaccuracy of the speed measurement shall be set to a value calculated from the LX speed, as defined in SUBSET-041 § 5.3.1.2: V_delta0lx = f41(V_LX)
- ListNumberText: b)
- kind: ordinary

###### 3.13.9.3.5.12 (Requirement Type)
To do so, the same formulas defined above with V_est and V_delta0 shall be applied, by substituting V_est with V_LX and V_delta0 with V_delta0lx.
- WordTraceId: 195554
- atomic: true
- Legal Obligation: mandatory
- implement: true
- implementerEnhanced: To do so, the same formulas defined
  above
  [WEAK]
  with V_est and V_delta0 shall be applied, by substituting V_est with V_LX and V_delta0 with V_delta0lx.
- kind: ordinary

###### 3.13.9.3.5.12[2] (Requirement Type)
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- WordTraceId: 195700
- atomic: true
- Legal Obligation: unknown
- implement: true
- kind: ordinary

###### 3.13.9.3.5.12[3] (Requirement Type)
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- WordTraceId: 195724
- atomic: true
- Legal Obligation: unknown
- implement: true
- kind: ordinary

###### 3.13.9.3.5.12[4] (Requirement Type)
with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
- WordTraceId: 195748
- atomic: true
- Legal Obligation: unknown
- PlainText: with
- implement: true
- implementerEnhanced: with
- kind: ordinary

###### 3.13.9.3.5.12[5] (Requirement Type)
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 if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
- WordTraceId: 195777
- atomic: true
- Legal Obligation: unknown
- PlainText: if
- implement: true
- implementerEnhanced: if
  [CONDITION]
- kind: ordinary

###### 3.13.9.3.5.12[6] (Requirement Type)
Or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 if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
- WordTraceId: 195828
- atomic: true
- Legal Obligation: unknown
- PlainText: Or  if
- implement: true
- implementerEnhanced: Or
  if
  [CONDITION]
- kind: ordinary

###### 3.13.9.3.5.12[7] (Requirement Type)
In case the GUI curve is inhibited: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
- WordTraceId: 195882
- atomic: true
- Legal Obligation: unknown
- PlainText: In case the GUI curve is inhibited:
- implement: true
- implementerEnhanced: In case
  [CONDITION]
  the GUI curve is inhibited:
- kind: ordinary

###### 3.13.9.3.5.12[8] (Requirement Type)
In case the GUI curve is enabled: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
- WordTraceId: 195942
- atomic: true
- Legal Obligation: unknown
- PlainText: In case the GUI curve is enabled:
- implement: true
- implementerEnhanced: In case
  [CONDITION]
  the GUI curve is enabled:
- kind: ordinary

###### 3.13.9.3.6 (Requirement Type)
Indication supervision limit (I)
- WordTraceId: 196000
- atomic: false
- Legal Obligation: not applicable
- implement: false
- kind: Heading

###### 3.13.9.3.6.1 (Requirement Type)
The on-board shall calculate the location of the Indication supervision limit valid for the estimated speed, assuming that this latter remains constant during the interval T_indication until the location of the Permitted speed supervision limit is reached.
- WordTraceId: 196033
- atomic: true
- Legal Obligation: mandatory
- implement: true
- implementerEnhanced: The on-board shall calculate the location of the Indication supervision limit valid for the estimated speed, assuming that this latter remains constant
  during
  [TIME]
  the interval T_indication
  until
  [TIME]
  the location of the Permitted speed supervision limit is reached.
- kind: ordinary

###### 3.13.9.3.6.1[2] (Requirement Type)
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- WordTraceId: 196290
- atomic: true
- Legal Obligation: unknown
- implement: true
- kind: ordinary

###### 3.13.9.3.6.2 (Requirement Type)
If the service brake feedback interface is not available for use, then
- WordTraceId: 196314
- atomic: true
- Legal Obligation: unknown
- implement: true
- implementerEnhanced: If
  [CONDITION]
  the service brake feedback interface is not available for use, then
- kind: ordinary

###### 3.13.9.3.6.2[2] (Requirement Type)
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- WordTraceId: 196385
- atomic: true
- Legal Obligation: unknown
- implement: true
- kind: ordinary

###### 3.13.9.3.6.3 (Requirement Type)
Note: The reduction of T_indication by a factor is intended to improve performance and the feasibility of this reduction is based on experience with real implementations. To avoid very low values when T_bs is small, a minimum is defined for T_indication, giving the driver always enough time to operate the brake.
- WordTraceId: 196409
- atomic: false
- Legal Obligation: not applicable
- implement: false
- implementerEnhanced: Note: The reduction of T_indication by a factor is intended to improve performance and the feasibility of this reduction is based on experience with real implementations. To avoid
  very
  [WEAK]
  low values
  when
  [CONDITION]
  T_bs is small, a minimum is defined for T_indication, giving the
  driver
  [EXTERNAL]
  always enough
  time
  [TIME]
  to operate the brake.
- kind: Note

###### 3.13.9.3.6.4 (Requirement Type)
If the service brake feedback interface is available for use then T_indication = 5s.
- WordTraceId: 196723
- atomic: true
- Legal Obligation: unknown
- implement: true
- implementerEnhanced: If
  [CONDITION]
  the service brake feedback interface is available for use then T_indication = 5s.
- kind: ordinary

##### 3.13.9.4 (Requirement Type)
Release speed supervision limits
- WordTraceId: 196808
- atomic: false
- Legal Obligation: not applicable
- implement: false
- kind: Heading

###### 3.13.9.4.1 (Requirement Type)
The release speed is a special ceiling speed limit, applicable in the vicinity of the EOA. The EBI supervision limit shall be equal to the release speed. There is no SBI, W, P, I supervision limit associated to the release speed.
- WordTraceId: 196841
- atomic: false
- Legal Obligation: mandatory
- implement: true
- kind: ordinary

###### 3.13.9.4.2 (Requirement Type)
Note: The release speed may be necessary for two reasons. One is that a train has to be able to approach the EOA where the permitted speed reaches zero and might be too restrictive to permit acceptable driving due to inaccuracy of the measured distance. The other reason is that in a level 1 application the train has to be able to overpass the balise when the signal clears. For these two reasons a (low) release speed may be given from trackside or may be calculated on board, based on the distance from the EOA to the Supervised Location.
- WordTraceId: 197071
- atomic: false
- Legal Obligation: optional
- implement: false
- implementerEnhanced: Note: The release speed may be necessary for two reasons. One is that a train has to be able to approach the EOA where the permitted speed reaches zero and might be too restrictive to permit acceptable driving due to inaccuracy of the measured distance. The
  other reason
  [WEAK]
  is that in a level 1 application the train has to be able to overpass the
  balise
  [EXTERNAL]
  when
  [CONDITION]
  the signal clears. For these two reasons a (low) release speed may be given from
  trackside
  [EXTERNAL]
  or may be calculated on board, based on the distance from the EOA to the Supervised Location.
- kind: Note

###### 3.13.9.4.3 (Requirement Type)
With each MA, it shall be possible for the trackside to:
- WordTraceId: 197613
- atomic: true
- Legal Obligation: mandatory
- implement: true
- implementerEnhanced: With each MA, it shall be possible for the
  trackside
  [EXTERNAL]
  to:
- kind: ordinary

###### 3.13.9.4.3.a (Requirement Type)
Give the value of the release speed directly to the on-board, OR
- WordTraceId: 197670
- atomic: true
- Legal Obligation: mandatory (== 1)
- implement: true
- ListNumberText: a)
- kind: ordinary

###### 3.13.9.4.3.b (Requirement Type)
Instruct the on-board to calculate the release speed, OR
- WordTraceId: 197735
- atomic: true
- Legal Obligation: mandatory (== 1)
- implement: true
- ListNumberText: b)
- kind: ordinary

###### 3.13.9.4.3.c (Requirement Type)
Instruct the on-board to use the national value.
- WordTraceId: 197792
- atomic: true
- Legal Obligation: mandatory (== 1)
- implement: true
- ListNumberText: c)
- kind: ordinary

###### 3.13.9.4.4 (Requirement Type)
In case the MA does not identify the variant to be used or in case of LOA, no release speed shall be supervised.
- WordTraceId: 197841
- atomic: true
- Legal Obligation: mandatory
- implement: true
- implementerEnhanced: In case
  [CONDITION]
  the MA does not identify the variant to be used or
  in case of
  [CONDITION]
  LOA, no release speed shall be supervised.
- kind: ordinary

###### 3.13.9.4.5 (Requirement Type)
Note: When the release speed is given as a fixed value from trackside, the ERTMS/ETCS system cannot be responsible for stopping the train in rear of the Supervised Location. In this case, it is the full responsibility of the infrastructure manager to set the appropriate release speed with regard to the risk of passing the Supervised Location.
- WordTraceId: 197954
- atomic: false
- Legal Obligation: not applicable
- implement: false
- implementerEnhanced: Note:
  When
  [CONDITION]
  the release speed is given as a fixed value from
  trackside
  [EXTERNAL]
  , the ERTMS/ETCS system cannot be responsible for stopping the train in rear of the Supervised Location. In this case, it is the full responsibility of the infrastructure manager to set the appropriate release speed with regard to the risk of passing the Supervised Location.
- kind: Note

###### 3.13.9.4.6 (Requirement Type)
The start location of the release speed monitoring (i.e. where the EBI supervision limit related to EBD is replaced with an EBI supervision limit equal to the release speed value) shall be the location of the FLOI supervision limit, calculated for the Release Speed value, taking into account the following assumptions:
- WordTraceId: 198299
- atomic: true
- Legal Obligation: not applicable
- implement: false
- kind: Heading

###### 3.13.9.4.6.a (Requirement Type)
the estimated acceleration shall be set to “zero”
- WordTraceId: 198619
- atomic: true
- Legal Obligation: mandatory
- implement: true
- ListNumberText: a)
- kind: ordinary

###### 3.13.9.4.6.b (Requirement Type)
if not inhibited by National Value, the compensation of the inaccuracy of the speed measurement shall be set to a value calculated from the release speed, as defined in SUBSET-041 § 5.3.1.2: V_delta0rs = f
41
(V_release)
- WordTraceId: 198669
- atomic: true
- Legal Obligation: mandatory
- PlainText: if not inhibited by National Value, the compensation of the inaccuracy of the speed measurement shall be set to a value calculated from the release speed, as defined in SUBSET-041 § 5.3.1.2: V_delta0rs = f41(V_release)
- implement: true
- implementerEnhanced: if
  [CONDITION]
  not inhibited by National Value, the compensation of the inaccuracy of the speed measurement shall be set to a value calculated from the release speed, as defined in SUBSET-041 § 5.3.1.2: V_delta0rs = f41(V_release)
- ListNumberText: b)
- kind: ordinary

###### 3.13.9.4.7 (Requirement Type)
To do so, the same formulas defined above with V_est and V_delta0 shall be applied, by substituting V_est with V_release and V_delta0 with V_delta0rs.
- WordTraceId: 198888
- atomic: true
- Legal Obligation: mandatory
- implement: true
- implementerEnhanced: To do so, the same formulas defined
  above
  [WEAK]
  with V_est and V_delta0 shall be applied, by substituting V_est with V_release and V_delta0 with V_delta0rs.
- kind: ordinary

###### 3.13.9.4.7[2] (Requirement Type)
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- WordTraceId: 199039
- atomic: true
- Legal Obligation: unknown
- implement: true
- kind: ordinary

###### 3.13.9.4.7[3] (Requirement Type)
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- WordTraceId: 199063
- atomic: true
- Legal Obligation: unknown
- implement: true
- kind: ordinary

###### 3.13.9.4.7[4] (Requirement Type)
with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
- WordTraceId: 199087
- atomic: true
- Legal Obligation: unknown
- PlainText: with
- implement: true
- implementerEnhanced: with
- kind: ordinary

###### 3.13.9.4.7[5] (Requirement Type)
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 if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
- WordTraceId: 199116
- atomic: true
- Legal Obligation: unknown
- PlainText: if
- implement: true
- implementerEnhanced: if
  [CONDITION]
- kind: ordinary

###### 3.13.9.4.7[6] (Requirement Type)
Or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 if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
- WordTraceId: 199167
- atomic: true
- Legal Obligation: unknown
- PlainText: Or  if
- implement: true
- implementerEnhanced: Or
  if
  [CONDITION]
- kind: ordinary

###### 3.13.9.4.7[7] (Requirement Type)
- WordTraceId: 199221
- atomic: false
- Legal Obligation: not applicable
- implement: false
- kind: Placeholder

###### 3.13.9.4.7[7].[f]50 (Requirement Type)
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- WordTraceId: 199249
- atomic: false
- Legal Obligation: not applicable
- implement: false
- kind: Figure

###### 3.13.9.4.7[7].[f]50.C (Requirement Type)
Figure {Figure 50}: Start location of Release Speed Monitoring
- WordTraceId: 199249
- atomic: true
- Legal Obligation: unknown
- PlainText: Figure 50: Start location of Release Speed Monitoring
- implement: false
- kind: Figure

###### 3.13.9.4.8 (Requirement Type)
When the Release Speed is calculated on-board (Figure 51 box 3), its value shall be equal to the most restrictive value, at the Trip location related to the EOA, amongst the EBI supervision limit related to the SvL (Figure 51 box 1) and, if any, the EBI supervision limits(s) related to other target(s) between the Trip location related to the EOA and the SvL (Figure 51 box 2).
- WordTraceId: 199328
- atomic: true
- Legal Obligation: mandatory
- implement: true
- implementerEnhanced: When
  [CONDITION]
  the Release Speed is calculated on-board (Figure 51 box 3), its value shall be equal to the most restrictive value, at the Trip location related to the EOA, amongst the EBI supervision limit related to the SvL (Figure 51 box 1) and,
  if
  [CONDITION]
  any, the EBI supervision limits(s) related to other target(s) between the Trip location related to the EOA and the SvL (Figure 51 box 2).
- kind: ordinary
- CrossRefLink -> 3.13.9.4.8[2].[f]51.C

###### 3.13.9.4.8[2] (Requirement Type)
- WordTraceId: 199785
- atomic: false
- Legal Obligation: not applicable
- implement: false
- kind: Placeholder

###### 3.13.9.4.8[2].[f]51 (Requirement Type)
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- WordTraceId: 199813
- atomic: false
- Legal Obligation: not applicable
- implement: false
- kind: Figure

###### 3.13.9.4.8[2].[f]51.C (Requirement Type)
Figure {Figure 51}: Calculated Release Speed based on speed restriction between EOA and SvL
- WordTraceId: 199813
- atomic: true
- Legal Obligation: unknown
- PlainText: Figure 51: Calculated Release Speed based on speed restriction between EOA and SvL
- implement: false
- kind: Figure

###### 3.13.9.4.8[2].1 (Requirement Type)
In order to calculate in advance the EBI supervision limit at the Trip location related to the EOA, the on-board equipment shall take into account an estimated acceleration set to “zero”.
- WordTraceId: 199921
- atomic: true
- Legal Obligation: mandatory
- implement: true
- implementerEnhanced: In order to calculate in advance the EBI supervision limit at the Trip location related to the EOA, the
  on-board equipment
  [SELF]
  shall take into account an estimated acceleration set to “zero”.
- ListNumberText: 3.13.9.4.8.1
- kind: ordinary

###### 3.13.9.4.8[2].2 (Requirement Type)
The release speed shall be iteratively calculated as follows:
- WordTraceId: 200109
- atomic: true
- Legal Obligation: mandatory
- implement: true
- ListNumberText: 3.13.9.4.8.2
- kind: ordinary

###### 3.13.9.4.8[2].2[2] (Requirement Type)
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- WordTraceId: 200171
- atomic: true
- Legal Obligation: unknown
- implement: true
- kind: ordinary

###### 3.13.9.4.8[2].2[3] (Requirement Type)
With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 or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 (if compensation of speed inaccuracy is inhibited by National Value)
- WordTraceId: 200195
- atomic: true
- Legal Obligation: unknown
- PlainText: With  or  (if compensation of speed inaccuracy is inhibited by National Value)
- implement: true
- implementerEnhanced: With or (
  if
  [CONDITION]
  compensation of speed inaccuracy is inhibited by National Value)
- kind: ordinary

###### 3.13.9.4.8[2].2[4] (Requirement Type)
With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
- WordTraceId: 200320
- atomic: true
- Legal Obligation: unknown
- PlainText: With
- implement: true
- implementerEnhanced: With
- kind: ordinary

###### 3.13.9.4.8[2].2[5] (Requirement Type)
With
- WordTraceId: 200349
- atomic: true
- Legal Obligation: unknown
- implement: true
- kind: ordinary

###### 3.13.9.4.8[2].2[6] (Requirement Type)
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- WordTraceId: 200354
- atomic: true
- Legal Obligation: unknown
- implement: true
- kind: ordinary

###### 3.13.9.4.8[2].2[7] (Requirement Type)
And with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 if level = 1
- WordTraceId: 200378
- atomic: true
- Legal Obligation: unknown
- PlainText: And with if level = 1
- implement: true
- implementerEnhanced: And with
  if
  [CONDITION]
  level = 1
- kind: ordinary

###### 3.13.9.4.8[2].2[8] (Requirement Type)
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 if level = 2 or 3
- WordTraceId: 200423
- atomic: true
- Legal Obligation: unknown
- PlainText: if level = 2 or 3
- implement: true
- implementerEnhanced: if
  [CONDITION]
  level = 2 or 3
- kind: ordinary

###### 3.13.9.4.8[2].2[9] (Requirement Type)
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 if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
- WordTraceId: 200466
- atomic: true
- Legal Obligation: unknown
- PlainText: if
- implement: true
- implementerEnhanced: if
  [CONDITION]
- kind: ordinary

###### 3.13.9.4.8[2].2[10] (Requirement Type)
or if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
- WordTraceId: 200517
- atomic: true
- Legal Obligation: unknown
- PlainText: or if
- implement: true
- implementerEnhanced: or
  if
  [CONDITION]
- kind: ordinary

###### 3.13.9.4.8[2].2[11] (Requirement Type)
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- WordTraceId: 200547
- atomic: true
- Legal Obligation: unknown
- implement: true
- kind: ordinary

###### 3.13.9.4.8[2].2[12] (Requirement Type)
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 as soon as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
- WordTraceId: 200571
- atomic: true
- Legal Obligation: unknown
- PlainText: as soon as
- implement: true
- implementerEnhanced: as soon as
  [WEAK]
- kind: ordinary

###### 3.13.9.4.8[2].2[13] (Requirement Type)
with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
- WordTraceId: 200630
- atomic: true
- Legal Obligation: unknown
- PlainText: with
- implement: true
- implementerEnhanced: with
- kind: ordinary

###### 3.13.9.4.8[2].2[13].1 (Requirement Type)
Note: The above formulas are intended to prevent the calculated release speed from fluctuating, according to the distance, speed and acceleration measurements. It allows calculating the release speed only once, for a given on-board reference location, unless
- WordTraceId: 200660
- atomic: false
- Legal Obligation: not applicable
- implement: false
- implementerEnhanced: Note: The
  above
  [WEAK]
  formulas are intended to prevent the calculated release speed from fluctuating, according to the distance, speed and acceleration measurements. It allows calculating the release speed only once, for a given on-board reference location, unless
- ListNumberText: 3.13.9.4.8.2.1
- kind: Note

###### 3.13.9.4.8[2].2[13].1.*[1] (Requirement Type)
the distance confidence interval exceeds a predicted one, which is based on the assumption that the whole distance between the current on-board reference location and the EOA would be travelled with SUBSET-041 odometer performance values and without any update of the on-board reference location, or
- WordTraceId: 200919
- atomic: true
- Legal Obligation: unknown
- implement: false
- ListNumberText: ·
- kind: Note

###### 3.13.9.4.8[2].2[13].1.*[2] (Requirement Type)
the speed under reading amount (V_ura) exceeds the SUBSET-041 performance value
- WordTraceId: 201219
- atomic: true
- Legal Obligation: unknown
- implement: false
- ListNumberText: ·
- kind: Note

###### 3.13.9.4.8[2].2[13].1[2] (Requirement Type)
Whenever the on-board reference location is updated (e.g. new LRBG), the release speed will however be recalculated and will increase with a step. This behaviour is acceptable from an operational point of view.
- WordTraceId: 201299
- atomic: false
- Legal Obligation: unknown
- implement: true
- implementerEnhanced: Whenever the on-board reference location is updated (
  e.g.
  [WEAK]
  new
  LRBG
  [EXTERNAL]
  ), the release speed will however be recalculated and will increase with a step. This behaviour is acceptable from an operational point of view.
- kind: ordinary

###### 3.13.9.4.9 (Requirement Type)
If the release speed (Figure 52 box 1 gives an example when it is calculated on-board) exceeds the MRSP anywhere in the area (Figure 52 box 2) delimited on one side by the presumed start location of the Release speed monitoring and on the other side by the trip location related to the EOA, the on-board shall use as a fixed release speed (Figure 52 box 4) the most restrictive value of the MRSP (Figure 52 box 3) within this area, and shall re-evaluate the start location of the Release speed monitoring accordingly.
- WordTraceId: 201510
- atomic: false
- Legal Obligation: mandatory
- implement: true
- implementerEnhanced: If
  [CONDITION]
  the release speed (Figure 52 box 1 gives an example
  when
  [CONDITION]
  it is calculated on-board) exceeds the MRSP anywhere in the area (Figure 52 box 2) delimited on one side by the presumed start location of the Release speed monitoring and on the other side by the trip location related to the EOA, the on-board shall use as a fixed release speed (Figure 52 box 4) the most restrictive value of the MRSP (Figure 52 box 3) within this area, and shall
  re-evaluate
  [AGAIN]
  the start location of the Release speed monitoring accordingly.
- kind: ordinary
- CrossRefLink -> 3.13.9.4.9[2].[f]52.C

###### 3.13.9.4.9[2] (Requirement Type)
- WordTraceId: 202132
- atomic: false
- Legal Obligation: not applicable
- implement: false
- kind: Placeholder

###### 3.13.9.4.9[2].[f]52 (Requirement Type)
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- WordTraceId: 202160
- atomic: false
- Legal Obligation: not applicable
- implement: false
- kind: Figure

###### 3.13.9.4.9[2].[f]52.C (Requirement Type)
Figure {Figure 52}: Release Speed limited by MRSP
- WordTraceId: 202160
- atomic: true
- Legal Obligation: unknown
- PlainText: Figure 52: Release Speed limited by MRSP
- implement: false
- implementerEnhanced: Figure 52: Release Speed limited by MRSP
- kind: Figure

##### 3.13.9.5 (Requirement Type)
Pre-indication location
- WordTraceId: 202226
- atomic: false
- Legal Obligation: not applicable
- implement: false
- kind: Heading

###### 3.13.9.5.1 (Requirement Type)
The purpose of the pre-indication is to inform the driver that he is approaching an area where he has to operate the service brake in order to brake to a target. The pre-indication is used to switch from ceiling speed monitoring to target speed monitoring.
- WordTraceId: 202250
- atomic: false
- Legal Obligation: unknown
- implement: true
- implementerEnhanced: The purpose of the pre-indication is to inform the
  driver
  [EXTERNAL]
  that he is approaching an area where he has to operate the service brake in order to brake to a target. The pre-indication is used to switch from ceiling speed monitoring to target speed monitoring.
- kind: ordinary

###### 3.13.9.5.2 (Requirement Type)
For an EBD based target, the on-board shall calculate the pre-indication location as follows.
- WordTraceId: 202507
- atomic: true
- Legal Obligation: mandatory
- implement: true
- kind: ordinary

###### 3.13.9.5.3 (Requirement Type)
Starting from the first element of the MRSP (i.e. from the start location of the on-board stored track description), the on-board shall calculate the location of the Indication supervision limit, valid for the speed of the MRSP element, taking into account the following assumptions:
- WordTraceId: 202601
- atomic: true
- Legal Obligation: not applicable
- implement: false
- kind: Heading

###### 3.13.9.5.3.a (Requirement Type)
the estimated acceleration shall be set to “zero”
- WordTraceId: 202885
- atomic: true
- Legal Obligation: mandatory
- implement: true
- ListNumberText: a)
- kind: ordinary

###### 3.13.9.5.3.b (Requirement Type)
if not inhibited by National Value, the compensation of the inaccuracy of the speed measurement shall be set to a value, calculated from the speed of the MRSP element, as defined in SUBSET-041 § 5.3.1.2: V_delta0ind = f
41
(V_MRSP-n)
- WordTraceId: 202935
- atomic: true
- Legal Obligation: mandatory
- PlainText: if not inhibited by National Value, the compensation of the inaccuracy of the speed measurement shall be set to a value, calculated from the speed of the MRSP element, as defined in SUBSET-041 § 5.3.1.2: V_delta0ind = f41(V_MRSP-n)
- implement: true
- implementerEnhanced: if
  [CONDITION]
  not inhibited by National Value, the compensation of the inaccuracy of the speed measurement shall be set to a value, calculated from the speed of the MRSP element, as defined in SUBSET-041 § 5.3.1.2: V_delta0ind = f41(V_MRSP-n)
- ListNumberText: b)
- kind: ordinary

###### 3.13.9.5.4 (Requirement Type)
To calculate the EBI supervision limit, the same formulas defined above with V_est and V_delta0 shall be applied, by substituting V_est with V_MRSP-n and V_delta0 with V_delta0ind.
- WordTraceId: 203167
- atomic: true
- Legal Obligation: mandatory
- implement: true
- implementerEnhanced: To calculate the EBI supervision limit, the same formulas defined
  above
  [WEAK]
  with V_est and V_delta0 shall be applied, by substituting V_est with V_MRSP-n and V_delta0 with V_delta0ind.
- kind: ordinary

###### 3.13.9.5.4[2] (Requirement Type)
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- WordTraceId: 203348
- atomic: true
- Legal Obligation: unknown
- implement: true
- kind: ordinary

###### 3.13.9.5.4[3] (Requirement Type)
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- WordTraceId: 203372
- atomic: true
- Legal Obligation: unknown
- implement: true
- kind: ordinary

###### 3.13.9.5.4[4] (Requirement Type)
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- WordTraceId: 203396
- atomic: true
- Legal Obligation: unknown
- implement: true
- kind: ordinary

###### 3.13.9.5.4[5] (Requirement Type)
With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 if the GUI curve is inhibited
- WordTraceId: 203420
- atomic: true
- Legal Obligation: unknown
- PlainText: With  if the GUI curve is inhibited
- implement: true
- implementerEnhanced: With
  if
  [CONDITION]
  the GUI curve is inhibited
- kind: ordinary

###### 3.13.9.5.4[6] (Requirement Type)
Or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 if the GUI curve is enabled
- WordTraceId: 203479
- atomic: true
- Legal Obligation: unknown
- PlainText: Or  if the GUI curve is enabled
- implement: true
- implementerEnhanced: Or
  if
  [CONDITION]
  the GUI curve is enabled
- kind: ordinary

###### 3.13.9.5.5 (Requirement Type)
If the Indication supervision limit, obtained from the speed of the n
th
element, is located between the start and end locations of this n
th
element, the pre-indication location shall be calculated as follows:
- WordTraceId: 203534
- atomic: true
- Legal Obligation: mandatory
- PlainText: If the Indication supervision limit, obtained from the speed of the nth element, is located between the start and end locations of this nth element, the pre-indication location shall be calculated as follows:
- implement: true
- implementerEnhanced: If
  [CONDITION]
  the Indication supervision limit, obtained from the speed of the nth element, is located between the start and end locations of this nth element, the pre-indication location shall be calculated as follows:
- kind: ordinary

###### 3.13.9.5.5[2] (Requirement Type)
If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
- WordTraceId: 203743
- atomic: true
- Legal Obligation: unknown
- PlainText: If
- implement: true
- implementerEnhanced: If
  [CONDITION]
- kind: ordinary

###### 3.13.9.5.5[3] (Requirement Type)
Then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
- WordTraceId: 203770
- atomic: true
- Legal Obligation: unknown
- PlainText: Then
- implement: true
- implementerEnhanced: Then
- kind: ordinary

###### 3.13.9.5.6 (Requirement Type)
If the Indication supervision limit, obtained from the speed of the n
th
element, is located in advance of the end location of this n
th
element, and if the Indication supervision limit, obtained from the speed of the n+1
th
element is located in rear of the end location of this n
th
element (see Figure 53), the pre-indication location shall be calculated as follows:
- WordTraceId: 203799
- atomic: true
- Legal Obligation: mandatory
- PlainText: If the Indication supervision limit, obtained from the speed of the nth element, is located in advance of the end location of this nth element, and if the Indication supervision limit, obtained from the speed of the n+1th element is located in rear of the end location of this nth element (see Figure 53), the pre-indication location shall be calculated as follows:
- implement: true
- implementerEnhanced: If
  [CONDITION]
  the Indication supervision limit, obtained from the speed of the nth element, is located in advance of the end location of this nth element, and
  if
  [CONDITION]
  the Indication supervision limit, obtained from the speed of the n+1th element is located in rear of the end location of this nth element (see Figure 53), the pre-indication location shall be calculated as follows:
- kind: ordinary
- CrossRefLink -> 3.13.9.5.6[4].[f]53.C

###### 3.13.9.5.6[2] (Requirement Type)
If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 and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
- WordTraceId: 204191
- atomic: true
- Legal Obligation: unknown
- PlainText: If   and
- implement: true
- implementerEnhanced: If
  [CONDITION]
  and
- kind: ordinary

###### 3.13.9.5.6[3] (Requirement Type)
Then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
- WordTraceId: 204248
- atomic: true
- Legal Obligation: unknown
- PlainText: Then
- implement: true
- implementerEnhanced: Then
- kind: ordinary

###### 3.13.9.5.6[4] (Requirement Type)
- WordTraceId: 204277
- atomic: false
- Legal Obligation: not applicable
- implement: false
- kind: Placeholder

###### 3.13.9.5.6[4].[f]53 (Requirement Type)
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- WordTraceId: 204305
- atomic: false
- Legal Obligation: not applicable
- implement: false
- kind: Figure

###### 3.13.9.5.6[4].[f]53.C (Requirement Type)
Figure {Figure 53}: Pre-indication location derived from MRSP speed increase
- WordTraceId: 204305
- atomic: true
- Legal Obligation: unknown
- PlainText: Figure 53: Pre-indication location derived from MRSP speed increase
- implement: false
- kind: Figure

###### 3.13.9.5.7 (Requirement Type)
T_preindication is defined as a fixed value (refer to A3.1).
- WordTraceId: 204398
- atomic: true
- Legal Obligation: unknown
- implement: false
- kind: Definition
- CrossRefLink -> A.3.1

###### 3.13.9.5.8 (Requirement Type)
For the EOA, the on-board shall calculate its pre-indication location in the same way as for an EBD based target, except that the formulas to calculate the distance between the location of the Indication supervision limit and the SBD shall be:
- WordTraceId: 204459
- atomic: false
- Legal Obligation: mandatory
- implement: true
- kind: ordinary

###### 3.13.9.5.8[2] (Requirement Type)
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- WordTraceId: 204703
- atomic: true
- Legal Obligation: unknown
- implement: true
- kind: ordinary

###### 3.13.9.5.8[3] (Requirement Type)
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- WordTraceId: 204727
- atomic: true
- Legal Obligation: unknown
- implement: true
- kind: ordinary

###### 3.13.9.5.8[4] (Requirement Type)
With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 if the GUI curve is inhibited
- WordTraceId: 204751
- atomic: true
- Legal Obligation: unknown
- PlainText: With  if the GUI curve is inhibited
- implement: true
- implementerEnhanced: With
  if
  [CONDITION]
  the GUI curve is inhibited
- kind: ordinary

###### 3.13.9.5.8[5] (Requirement Type)
Or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if the GUI curve is enabled
- WordTraceId: 204810
- atomic: true
- Legal Obligation: unknown
- PlainText: Or if the GUI curve is enabled
- implement: true
- implementerEnhanced: Or
  if
  [CONDITION]
  the GUI curve is enabled
- kind: ordinary

###### 3.13.9.5.9 (Requirement Type)
If, in exceptional situation (e.g. after a shortening of MA), the calculation described above leads to a pre-indication location in rear of the start location of the MRSP, the condition [1] for executing speed monitoring transition (see Table 16) shall be considered as immediately fulfilled.
- WordTraceId: 204864
- atomic: true
- Legal Obligation: mandatory
- implement: true
- implementerEnhanced: If
  [CONDITION]
  , in exceptional situation (
  e.g.
  [WEAK]
  after
  [TIME]
  a shortening of MA), the calculation described
  above
  [WEAK]
  leads to a pre-indication location in rear of the start location of the MRSP, the condition [1] for executing speed monitoring transition (see Table 16) shall be considered as
  immediately
  [WEAK]
  fulfilled.
- kind: ordinary
- CrossRefLink -> 3.13.10.6.1[2].[t]16.C

###### 3.13.9.5.10 (Requirement Type)
If, in exceptional situation (e.g. after a shortening of MA), the EBD, SBD or GUI speed at the start location of the MRSP is lower than the speed of the first element of the MRSP, the condition [1] for executing speed monitoring transition (see Table 16) shall be considered as immediately fulfilled.
- WordTraceId: 205183
- atomic: true
- Legal Obligation: mandatory
- implement: true
- implementerEnhanced: If
  [CONDITION]
  , in exceptional situation (
  e.g.
  [WEAK]
  after
  [TIME]
  a shortening of MA), the EBD, SBD or GUI speed at the start location of the MRSP is lower than the speed of the first element of the MRSP, the condition [1] for executing speed monitoring transition (see Table 16) shall be considered as
  immediately
  [WEAK]
  fulfilled.
- kind: ordinary
- CrossRefLink -> 3.13.10.6.1[2].[t]16.C

###### 3.13.9.5.11 (Requirement Type)
Note 1: For ergonomic reasons, the location of a pre-indication is independent of the estimated speed. If the pre-indication would be derived from an EBD or SBD curve according to the estimated speed, then when the train is running at low speed the driver would see the permitted speed already decrease while the DMI is still in ceiling speed display. That is not consistent for the driver and therefore the pre-indication is independent of the estimated speed.
- WordTraceId: 205510
- atomic: false
- Legal Obligation: not applicable
- implement: false
- implementerEnhanced: Note 1: For ergonomic reasons, the location of a pre-indication is independent of the estimated speed.
  If
  [CONDITION]
  the pre-indication would be derived from an EBD or SBD curve according to the estimated speed, then
  when
  [CONDITION]
  the train is running at low speed the
  driver
  [EXTERNAL]
  would see the permitted speed already decrease
  while
  [TIME]
  the DMI is still in ceiling speed display. That is not consistent for the
  driver
  [EXTERNAL]
  and therefore the pre-indication is independent of the estimated speed.
- kind: Note

###### 3.13.9.5.12 (Requirement Type)
Note 2: For trackside engineering reasons, the assumptions for the calculation of the EBI supervision limit are necessary to obtain a fully predictable pre-indication location, i.e. independent from the measured acceleration and speed confidence interval.
- WordTraceId: 205972
- atomic: false
- Legal Obligation: not applicable
- implement: false
- implementerEnhanced: Note 2: For
  trackside
  [EXTERNAL]
  engineering reasons, the assumptions for the calculation of the EBI supervision limit are necessary to obtain a fully predictable pre-indication location, i.e. independent from the measured acceleration and speed confidence interval.
- kind: Note

###### 3.13.9.5.13 (Requirement Type)
For display purpose only: when the pre-indication location of the target is derived from the location of the Indication supervision limit, this latter is used in order to discriminate, for estimated speeds higher than the MRSP speed, whether the on-board considers that the Indication supervision limit is exceeded (see section 3.13.10.4.11).
- WordTraceId: 206228
- atomic: true
- Legal Obligation: unknown
- implement: true
- implementerEnhanced: For display purpose only:
  when
  [CONDITION]
  the pre-indication location of the target is derived from the location of the Indication supervision limit, this latter is used in order to discriminate, for estimated speeds higher than the MRSP speed,
  whether
  [CONDITION]
  the on-board considers that the Indication supervision limit is exceeded (see section 3.13.10.4.11).
- kind: ordinary
- CrossRefLink -> 3.13.10.4.11

#### 3.13.10 (Requirement Type)
Speed and distance monitoring commands
- WordTraceId: 206600
- atomic: false
- Legal Obligation: not applicable
- implement: false
- kind: Heading

##### 3.13.10.1 (Requirement Type)
Introduction
- WordTraceId: 206639
- atomic: false
- Legal Obligation: not applicable
- implement: false
- kind: Heading

###### 3.13.10.1.1 (Requirement Type)
By comparing the train speed and position to the various supervision limits defined in the previous section, the on-board equipment generates braking commands, traction cut-off commands and relevant information to the driver. The information displayed to the driver is selected according to the following supervision statuses of the speed and distance monitoring function: Normal status, Indication status, Overspeed status, Warning status and Intervention status.
- WordTraceId: 206652
- atomic: false
- Legal Obligation: unknown
- implement: true
- implementerEnhanced: By comparing the train speed and position to the various supervision limits defined in the previous section, the
  on-board equipment
  [SELF]
  generates braking commands, traction cut-off commands and relevant information to the
  driver
  [EXTERNAL]
  . The information displayed to the
  driver
  [EXTERNAL]
  is selected according to the following supervision statuses of the speed and distance monitoring function: Normal status, Indication status, Overspeed status, Warning status and Intervention status.
- kind: ordinary

###### 3.13.10.1.2 (Requirement Type)
The following types of speed and distance monitoring are defined:
- WordTraceId: 207117
- atomic: true
- Legal Obligation: unknown
- implement: false
- kind: Heading

###### 3.13.10.1.2.*[1] (Requirement Type)
Ceiling speed monitoring (CSM)
- WordTraceId: 207183
- atomic: true
- Legal Obligation: unknown
- implement: false
- ListNumberText: ·
- kind: Definition

###### 3.13.10.1.2.*[2] (Requirement Type)
Target speed monitoring (TSM)
- WordTraceId: 207214
- atomic: true
- Legal Obligation: unknown
- implement: false
- ListNumberText: ·
- kind: Definition

###### 3.13.10.1.2.*[3] (Requirement Type)
Release speed monitoring (RSM)
- WordTraceId: 207244
- atomic: true
- Legal Obligation: unknown
- implement: false
- ListNumberText: ·
- kind: Definition

###### 3.13.10.1.2.*[3][2] (Requirement Type)
- WordTraceId: 207275
- atomic: false
- Legal Obligation: not applicable
- implement: false
- kind: Placeholder

###### 3.13.10.1.2.*[3][2].[f]54 (Requirement Type)
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- WordTraceId: 207303
- atomic: false
- Legal Obligation: not applicable
- implement: false
- kind: Figure

###### 3.13.10.1.2.*[3][2].[f]54.C (Requirement Type)
Figure {Figure 54}: Different types of speed and distance monitoring
- WordTraceId: 207303
- atomic: true
- Legal Obligation: unknown
- PlainText: Figure 54: Different types of speed and distance monitoring
- implement: false
- kind: Figure

###### 3.13.10.1.3 (Requirement Type)
Ceiling speed monitoring is the speed supervision in the area where the train can run with the speed as defined by the MRSP without the need to brake to a target.
- WordTraceId: 207388
- atomic: true
- Legal Obligation: unknown
- implement: true
- kind: ordinary

###### 3.13.10.1.4 (Requirement Type)
Target speed monitoring is the speed and distance supervision in the area where the specific information related to a target is displayed to the driver and within which the train brakes to a target.
- WordTraceId: 207551
- atomic: true
- Legal Obligation: unknown
- implement: true
- implementerEnhanced: Target speed monitoring is the speed and distance supervision in the area where the specific information related to a target is displayed to the
  driver
  [EXTERNAL]
  and within which the train brakes to a target.
- kind: ordinary

###### 3.13.10.1.5 (Requirement Type)
Release speed monitoring is the speed and distance supervision in the area close to the EOA where the train is allowed to run with release speed to approach the EOA.
- WordTraceId: 207750
- atomic: true
- Legal Obligation: unknown
- implement: true
- kind: ordinary

##### 3.13.10.2 (Requirement Type)
General requirements
- WordTraceId: 207916
- atomic: false
- Legal Obligation: not applicable
- implement: false
- kind: Heading

###### 3.13.10.2.1 (Requirement Type)
The train speed indicated to the driver shall be identical to the speed used for the speed monitoring (i.e. the estimated speed).
- WordTraceId: 207937
- atomic: true
- Legal Obligation: mandatory
- implement: true
- implementerEnhanced: The train speed indicated to the
  driver
  [EXTERNAL]
  shall be identical to the speed used for the speed monitoring (i.e. the estimated speed).
- kind: ordinary

###### 3.13.10.2.2 (Requirement Type)
Once a Train Interface command (traction cut-off, service brake or emergency brake) is triggered, the on-board shall apply it until its corresponding revocation condition is met.
- WordTraceId: 208067
- atomic: true
- Legal Obligation: mandatory
- implement: true
- implementerEnhanced: Once a Train Interface command (traction cut-off, service brake or emergency brake) is triggered, the on-board shall apply it
  until
  [TIME]
  its corresponding revocation condition is met.
- kind: ordinary

###### 3.13.10.2.3 (Requirement Type)
If there is no on-board interface with the service brake or if the use of the service brake command is not allowed by a National Value (only in Target speed monitoring), whenever a service brake command is specified, the emergency brake command shall be triggered instead.
- WordTraceId: 208246
- atomic: true
- Legal Obligation: mandatory
- implement: true
- implementerEnhanced: If
  [CONDITION]
  there is no on-board interface with the service brake or
  if
  [CONDITION]
  the use of the service brake command is not allowed by a National Value (only in Target speed monitoring), whenever a service brake command is specified, the emergency brake command shall be triggered instead.
- kind: ordinary

###### 3.13.10.2.4 (Requirement Type)
The emergency brake command, which is triggered instead of the service brake command when an SBI supervision limit is exceeded, shall be revoked according to the requirements specified for the revocation of service brake command, unless the emergency brake command has been also triggered due to an EBI supervision limit. In such case, the condition for revoking the emergency brake command due to EBI supervision limit shall prevail.
- WordTraceId: 208519
- atomic: false
- Legal Obligation: mandatory
- implement: true
- implementerEnhanced: The emergency brake command, which is triggered instead of the service brake command
  when
  [CONDITION]
  an SBI supervision limit is exceeded, shall be revoked according to the requirements specified for the revocation of service brake command, unless the emergency brake command has been also triggered due to an EBI supervision limit. In such case, the condition for revoking the emergency brake command due to EBI supervision limit shall prevail.
- kind: ordinary

###### 3.13.10.2.5 (Requirement Type)
The on-board shall revoke the Intervention status only when no brake command is applied by the speed and distance monitoring function.
- WordTraceId: 208954
- atomic: true
- Legal Obligation: mandatory
- implement: true
- implementerEnhanced: The on-board shall revoke the Intervention status only
  when
  [CONDITION]
  no brake command is applied by the speed and distance monitoring function.
- kind: ordinary

###### 3.13.10.2.6 (Requirement Type)
In level 2/3: Train trip shall be initiated if the on-board equipment detects that the minimum safe front end has passed the EOA/LOA location.
- WordTraceId: 209089
- atomic: true
- Legal Obligation: mandatory
- implement: true
- implementerEnhanced: In level 2/3: Train trip shall be initiated
  if
  [CONDITION]
  the
  on-board equipment
  [SELF]
  detects that the minimum safe front end has passed the EOA/LOA location.
- kind: ordinary

###### 3.13.10.2.7 (Requirement Type)
In Level 1: Train Trip shall be initiated if the on-board equipment detects that the minimum safe antenna position (calculated by subtracting distance between active Eurobalise antenna and the front end of the train from the min safe front end position) has passed the EOA/LOA location.
- WordTraceId: 209232
- atomic: true
- Legal Obligation: mandatory
- implement: true
- implementerEnhanced: In Level 1: Train Trip shall be initiated
  if
  [CONDITION]
  the
  on-board equipment
  [SELF]
  detects that the minimum safe antenna position (calculated by subtracting distance between active Eurobalise antenna and the front end of the train from the min safe front end position) has passed the EOA/LOA location.
- kind: ordinary

##### 3.13.10.3 (Requirement Type)
Requirements for Ceiling speed monitoring
- WordTraceId: 209519
- atomic: false
- Legal Obligation: not applicable
- implement: false
- kind: Heading

###### 3.13.10.3.1 (Requirement Type)
The on-board equipment shall display the Permitted speed.
- WordTraceId: 209561
- atomic: true
- Legal Obligation: mandatory
- implement: true
- implementerEnhanced: The
  on-board equipment
  [SELF]
  shall display the Permitted speed.
- kind: ordinary

###### 3.13.10.3.2 (Requirement Type)
When the supervision status is Overspeed, Warning or Intervention, the on-board equipment shall display the SBI speed (i.e. the FLOI speed).
- WordTraceId: 209619
- atomic: true
- Legal Obligation: mandatory
- implement: true
- implementerEnhanced: When
  [CONDITION]
  the supervision status is Overspeed, Warning or Intervention, the
  on-board equipment
  [SELF]
  shall display the SBI speed (i.e. the FLOI speed).
- kind: ordinary

###### 3.13.10.3.3 (Requirement Type)
The on-board shall compare the estimated speed with the ceiling supervision limits defined in section 3.13.9.2 and shall trigger/revoke commands to the train interface (service brake if implemented or emergency brake) and supervision statuses as described in Table 5 and Table 6.
- WordTraceId: 209760
- atomic: false
- Legal Obligation: mandatory
- implement: true
- implementerEnhanced: The on-board shall compare the estimated speed with the ceiling supervision limits defined in section 3.13.9.2 and shall trigger/revoke commands to the train interface (service brake
  if
  [CONDITION]
  implemented or emergency brake) and supervision statuses as described in Table 5 and Table 6.
- kind: ordinary
- CrossRefLink -> 3.13.9.2
- CrossRefLink -> 3.13.10.3.3[2].[t]5.C
- CrossRefLink -> 3.13.10.3.3[3].[t]6.C

###### 3.13.10.3.3[2] (Requirement Type)
- WordTraceId: 210121
- atomic: false
- Legal Obligation: not applicable
- implement: false
- kind: Placeholder

###### 3.13.10.3.3[2].[t]5 (Requirement Type)
| Triggeringcondition # | Estimated speed | Location | TI Command triggered | Supervision status triggered |
| --- | --- | --- | --- | --- |
| t1 | [C]1.Speed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 | [C]1.Position Any | [C]1.TICommand - | [C]1.Supervision Normal Status |
| t2 | [C]2.Speed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 | [C]2.Position Any | [C]2.TICommand - | [C]2.Supervision Overspeed Status |
| t3 | [C]3.Speed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 | [C]3.Position Any | [C]3.TICommand - | [C]3.Supervision Warning Status |
| t4 | [C]4.Speed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 | [C]4.Position Any | [C]4.TICommand SB | [C]4.Supervision Intervention Status |
| t5 | [C]5.Speed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 | [C]5.Position Any | [C]5.TICommand EB | [C]5.Supervision Intervention Status |
- WordTraceId: 210477
- atomic: false
- Legal Obligation: not applicable
- implement: false
- kind: Table

###### 3.13.10.3.3[2].[t]5.C (Requirement Type)
Table {Table 5}: triggering of Train Interface commands and supervision statuses in ceiling speed monitoring
- WordTraceId: 210477
- atomic: true
- Legal Obligation: unknown
- PlainText: Table 5: triggering of Train Interface commands and supervision statuses in ceiling speed monitoring
- implement: false
- kind: Table

###### 3.13.10.3.3[2].[t]5.[C]1 (Requirement Type)
- WordTraceId: 210219
- atomic: false
- Legal Obligation: not applicable
- implement: false
- kind: Table

###### 3.13.10.3.3[2].[t]5.[C]1.Speed (Requirement Type)
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- WordTraceId: 210222
- atomic: true
- Legal Obligation: unknown
- implement: true
- kind: ordinary

###### 3.13.10.3.3[2].[t]5.[C]1.Position (Requirement Type)
Any
- WordTraceId: 210246
- atomic: true
- Legal Obligation: unknown
- implement: true
- kind: ordinary

###### 3.13.10.3.3[2].[t]5.[C]1.TICommand (Requirement Type)
-
- WordTraceId: 210250
- atomic: true
- Legal Obligation: unknown
- implement: true
- kind: ordinary

###### 3.13.10.3.3[2].[t]5.[C]1.Supervision (Requirement Type)
Normal Status
- WordTraceId: 210252
- atomic: true
- Legal Obligation: unknown
- implement: true
- kind: ordinary

###### 3.13.10.3.3[2].[t]5.[C]2 (Requirement Type)
- WordTraceId: 210267
- atomic: false
- Legal Obligation: not applicable
- implement: false
- kind: Table

###### 3.13.10.3.3[2].[t]5.[C]2.Speed (Requirement Type)
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- WordTraceId: 210270
- atomic: true
- Legal Obligation: unknown
- implement: true
- kind: ordinary

###### 3.13.10.3.3[2].[t]5.[C]2.Position (Requirement Type)
Any
- WordTraceId: 210294
- atomic: true
- Legal Obligation: unknown
- implement: true
- kind: ordinary

###### 3.13.10.3.3[2].[t]5.[C]2.TICommand (Requirement Type)
-
- WordTraceId: 210298
- atomic: true
- Legal Obligation: unknown
- implement: true
- kind: ordinary

###### 3.13.10.3.3[2].[t]5.[C]2.Supervision (Requirement Type)
Overspeed Status
- WordTraceId: 210300
- atomic: true
- Legal Obligation: unknown
- implement: true
- kind: ordinary

###### 3.13.10.3.3[2].[t]5.[C]3 (Requirement Type)
- WordTraceId: 210318
- atomic: false
- Legal Obligation: not applicable
- implement: false
- kind: Table

###### 3.13.10.3.3[2].[t]5.[C]3.Speed (Requirement Type)
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- WordTraceId: 210321
- atomic: true
- Legal Obligation: unknown
- implement: true
- kind: ordinary

###### 3.13.10.3.3[2].[t]5.[C]3.Position (Requirement Type)
Any
- WordTraceId: 210345
- atomic: true
- Legal Obligation: unknown
- implement: true
- kind: ordinary

###### 3.13.10.3.3[2].[t]5.[C]3.TICommand (Requirement Type)
-
- WordTraceId: 210349
- atomic: true
- Legal Obligation: unknown
- implement: true
- kind: ordinary

###### 3.13.10.3.3[2].[t]5.[C]3.Supervision (Requirement Type)
Warning Status
- WordTraceId: 210351
- atomic: true
- Legal Obligation: unknown
- implement: true
- kind: ordinary

###### 3.13.10.3.3[2].[t]5.[C]4 (Requirement Type)
- WordTraceId: 210367
- atomic: false
- Legal Obligation: not applicable
- implement: false
- kind: Table

###### 3.13.10.3.3[2].[t]5.[C]4.Speed (Requirement Type)
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- WordTraceId: 210370
- atomic: true
- Legal Obligation: unknown
- implement: true
- kind: ordinary

###### 3.13.10.3.3[2].[t]5.[C]4.Position (Requirement Type)
Any
- WordTraceId: 210394
- atomic: true
- Legal Obligation: unknown
- implement: true
- kind: ordinary

###### 3.13.10.3.3[2].[t]5.[C]4.TICommand (Requirement Type)
SB
- WordTraceId: 210398
- atomic: true
- Legal Obligation: unknown
- implement: true
- kind: ordinary

###### 3.13.10.3.3[2].[t]5.[C]4.Supervision (Requirement Type)
Intervention Status
- WordTraceId: 210401
- atomic: true
- Legal Obligation: unknown
- implement: true
- kind: ordinary

###### 3.13.10.3.3[2].[t]5.[C]5 (Requirement Type)
- WordTraceId: 210422
- atomic: false
- Legal Obligation: not applicable
- implement: false
- kind: Table

###### 3.13.10.3.3[2].[t]5.[C]5.Speed (Requirement Type)
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- WordTraceId: 210425
- atomic: true
- Legal Obligation: unknown
- implement: true
- kind: ordinary

###### 3.13.10.3.3[2].[t]5.[C]5.Position (Requirement Type)
Any
- WordTraceId: 210449
- atomic: true
- Legal Obligation: unknown
- implement: true
- kind: ordinary

###### 3.13.10.3.3[2].[t]5.[C]5.TICommand (Requirement Type)
EB
- WordTraceId: 210453
- atomic: true
- Legal Obligation: unknown
- implement: true
- kind: ordinary

###### 3.13.10.3.3[2].[t]5.[C]5.Supervision (Requirement Type)
Intervention Status
- WordTraceId: 210456
- atomic: true
- Legal Obligation: unknown
- implement: true
- kind: ordinary

###### 3.13.10.3.3[3] (Requirement Type)
- WordTraceId: 210603
- atomic: false
- Legal Obligation: not applicable
- implement: false
- kind: Placeholder

###### 3.13.10.3.3[3].[t]6 (Requirement Type)
| Revocation condition # | Estimated speed | Location | TI Command revoked | Supervision status revoked |
| --- | --- | --- | --- | --- |
| r0 | [C]0.Position Standstill |  | [C]0.TICommand EB | [C]0.Supervision Intervention Status |
| r1 | [C]1.Speed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 | [C]1.Position Any | [C]1.TICommand SB EB (only if allowed by National Value) | [C]1.Supervision Indication Status Overspeed Status Warning Status Intervention Status (in case of EB command, only if allowed by National Value) |
- WordTraceId: 210941
- atomic: false
- Legal Obligation: not applicable
- implement: false
- kind: Table

###### 3.13.10.3.3[3].[t]6.C (Requirement Type)
Table {Table 6}: Revocation of Train Interface commands and supervision statuses in ceiling speed monitoring
- WordTraceId: 210941
- atomic: true
- Legal Obligation: unknown
- PlainText: Table 6: Revocation of Train Interface commands and supervision statuses in ceiling speed monitoring
- implement: false
- kind: Table

###### 3.13.10.3.3[3].[t]6.[C]0 (Requirement Type)
- WordTraceId: 210700
- atomic: false
- Legal Obligation: not applicable
- implement: false
- kind: Table

###### 3.13.10.3.3[3].[t]6.[C]0.Position (Requirement Type)
Standstill
- WordTraceId: 210703
- atomic: true
- Legal Obligation: unknown
- implement: true
- kind: ordinary

###### 3.13.10.3.3[3].[t]6.[C]0.TICommand (Requirement Type)
EB
- WordTraceId: 210714
- atomic: true
- Legal Obligation: unknown
- implement: true
- kind: ordinary

###### 3.13.10.3.3[3].[t]6.[C]0.Supervision (Requirement Type)
Intervention Status
- WordTraceId: 210717
- atomic: true
- Legal Obligation: unknown
- implement: true
- kind: ordinary

###### 3.13.10.3.3[3].[t]6.[C]1 (Requirement Type)
- WordTraceId: 210738
- atomic: false
- Legal Obligation: not applicable
- implement: false
- kind: Table

###### 3.13.10.3.3[3].[t]6.[C]1.Speed (Requirement Type)
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- WordTraceId: 210741
- atomic: true
- Legal Obligation: unknown
- implement: true
- kind: ordinary

###### 3.13.10.3.3[3].[t]6.[C]1.Position (Requirement Type)
Any
- WordTraceId: 210765
- atomic: true
- Legal Obligation: unknown
- implement: true
- kind: ordinary

###### 3.13.10.3.3[3].[t]6.[C]1.TICommand (Requirement Type)
CONTENTS HAVE BEEN SPLIT UP - SEE CHILDREN
- WordTraceId: 210769
- atomic: false
- Legal Obligation: not applicable
- implement: false
- kind: ordinary

###### 3.13.10.3.3[3].[t]6.[C]1.TICommand.[1] (Requirement Type)
SB
- WordTraceId: 210769
- atomic: true
- Legal Obligation: unknown
- implement: true
- kind: ordinary

###### 3.13.10.3.3[3].[t]6.[C]1.TICommand.[2] (Requirement Type)
EB (only if allowed by National Value)
- WordTraceId: 210772
- atomic: true
- Legal Obligation: unknown
- implement: true
- implementerEnhanced: EB (only
  if
  [CONDITION]
  allowed by National Value)
- kind: ordinary

###### 3.13.10.3.3[3].[t]6.[C]1.Supervision (Requirement Type)
CONTENTS HAVE BEEN SPLIT UP - SEE CHILDREN
- WordTraceId: 210811
- atomic: false
- Legal Obligation: not applicable
- implement: false
- kind: ordinary

###### 3.13.10.3.3[3].[t]6.[C]1.Supervision.[1] (Requirement Type)
Indication Status
- WordTraceId: 210811
- atomic: true
- Legal Obligation: unknown
- implement: true
- kind: ordinary

###### 3.13.10.3.3[3].[t]6.[C]1.Supervision.[2] (Requirement Type)
Overspeed Status
- WordTraceId: 210829
- atomic: true
- Legal Obligation: unknown
- implement: true
- kind: ordinary

###### 3.13.10.3.3[3].[t]6.[C]1.Supervision.[3] (Requirement Type)
Warning Status
- WordTraceId: 210846
- atomic: true
- Legal Obligation: unknown
- implement: true
- kind: ordinary

###### 3.13.10.3.3[3].[t]6.[C]1.Supervision.[4] (Requirement Type)
Intervention Status (in case of EB command, only if allowed by National Value)
- WordTraceId: 210861
- atomic: true
- Legal Obligation: unknown
- implement: true
- implementerEnhanced: Intervention Status (
  in case of
  [CONDITION]
  EB command, only
  if
  [CONDITION]
  allowed by National Value)
- kind: ordinary

###### 3.13.10.3.4 (Requirement Type)
The on-board equipment shall execute the transitions between the different supervision statuses as described in Table 7 (see section 4.6.1 for details about the symbols). This table takes into account the order of precedence between the supervision statuses and the possible updates of the MRSP while in ceiling speed monitoring (e.g. when a TSR is revoked).
- WordTraceId: 211067
- atomic: false
- Legal Obligation: mandatory
- implement: true
- implementerEnhanced: The
  on-board equipment
  [SELF]
  shall execute the transitions between the different supervision statuses as described in Table 7 (see section 4.6.1 for details about the symbols). This table takes into account the order of precedence between the supervision statuses and the possible updates of the MRSP
  while
  [TIME]
  in ceiling speed monitoring (
  e.g.
  [WEAK]
  when
  [CONDITION]
  a TSR is revoked).
- kind: ordinary
- CrossRefLink -> 3.13.10.3.4[2].[t]7.C
- CrossRefLink -> 4.6.1

###### 3.13.10.3.4[2] (Requirement Type)
- WordTraceId: 211452
- atomic: false
- Legal Obligation: not applicable
- implement: false
- kind: Placeholder

###### 3.13.10.3.4[2].[t]7 (Requirement Type)
| Normal status | [r][1].Indicationstatus_Normalstatus < r1 -p1- | [r][1].Overspeedstatus_Normalstatus < r1 -p1- | [r][1].Warningstatus_Normalstatus < r1 -p1- | [r][1].Interventionstatus_Normalstatus < r0, r1 -p1- |
| --- | --- | --- | --- | --- |
|  | Indication status |  |  |  |
| [r][3].Normalstatus_Overspeedstatus t2 > -p3- | [r][3].Indicationstatus_Overspeedstatus t2 > -p3- | Overspeed status |  |  |
| [r][4].Normalstatus_Warningstatus t3 > -p2- | [r][4].Indicationstatus_Warningstatus t3 > -p2- | [r][4].Overspeedstatus_Warningstatus t3 > -p2 | Warning status |  |
| [r][5].Normalstatus_Interventionstatus t4, t5 > -p1- | [r][5].Indicationstatus_Interventionstatus t4, t5 > -p1- | [r][5].Overspeedstatus_Interventionstatus t4, t5 > -p1- | [r][5].Warningstatus_Interventionstatus t4, t5 > -p1- | Intervention status |
- WordTraceId: 211697
- atomic: false
- Legal Obligation: not applicable
- implement: false
- kind: Table

###### 3.13.10.3.4[2].[t]7.C (Requirement Type)
Table {Table 7}: Transitions between supervision statuses in ceiling speed monitoring
- WordTraceId: 211697
- atomic: true
- Legal Obligation: unknown
- PlainText: Table 7: Transitions between supervision statuses in ceiling speed monitoring
- implement: false
- kind: Table

###### 3.13.10.3.4[2].[t]7.[r][1] (Requirement Type)
- WordTraceId: 211452
- atomic: false
- Legal Obligation: not applicable
- implement: false
- kind: Table

###### 3.13.10.3.4[2].[t]7.[r][1].Indicationstatus_Normalstatus (Requirement Type)
< r1
-p1-
- WordTraceId: 211466
- atomic: true
- Legal Obligation: unknown
- PlainText: < r1 -p1-
- implement: true
- kind: ordinary

###### 3.13.10.3.4[2].[t]7.[r][1].Overspeedstatus_Normalstatus (Requirement Type)
< r1
-p1-
- WordTraceId: 211476
- atomic: true
- Legal Obligation: unknown
- PlainText: < r1 -p1-
- implement: true
- kind: ordinary

###### 3.13.10.3.4[2].[t]7.[r][1].Warningstatus_Normalstatus (Requirement Type)
< r1
-p1-
- WordTraceId: 211486
- atomic: true
- Legal Obligation: unknown
- PlainText: < r1 -p1-
- implement: true
- kind: ordinary

###### 3.13.10.3.4[2].[t]7.[r][1].Interventionstatus_Normalstatus (Requirement Type)
< r0, r1
-p1-
- WordTraceId: 211496
- atomic: true
- Legal Obligation: unknown
- PlainText: < r0, r1 -p1-
- implement: true
- kind: ordinary

###### 3.13.10.3.4[2].[t]7.[r][3] (Requirement Type)
- WordTraceId: 211534
- atomic: false
- Legal Obligation: not applicable
- implement: false
- kind: Table

###### 3.13.10.3.4[2].[t]7.[r][3].Normalstatus_Overspeedstatus (Requirement Type)
t2 >
-p3-
- WordTraceId: 211534
- atomic: true
- Legal Obligation: unknown
- PlainText: t2 > -p3-
- implement: true
- kind: ordinary

###### 3.13.10.3.4[2].[t]7.[r][3].Indicationstatus_Overspeedstatus (Requirement Type)
t2 >
-p3-
- WordTraceId: 211544
- atomic: true
- Legal Obligation: unknown
- PlainText: t2 > -p3-
- implement: true
- kind: ordinary

###### 3.13.10.3.4[2].[t]7.[r][4] (Requirement Type)
- WordTraceId: 211574
- atomic: false
- Legal Obligation: not applicable
- implement: false
- kind: Table

###### 3.13.10.3.4[2].[t]7.[r][4].Normalstatus_Warningstatus (Requirement Type)
t3 >
-p2-
- WordTraceId: 211574
- atomic: true
- Legal Obligation: unknown
- PlainText: t3 > -p2-
- implement: true
- kind: ordinary

###### 3.13.10.3.4[2].[t]7.[r][4].Indicationstatus_Warningstatus (Requirement Type)
t3 >
-p2-
- WordTraceId: 211584
- atomic: true
- Legal Obligation: unknown
- PlainText: t3 > -p2-
- implement: true
- kind: ordinary

###### 3.13.10.3.4[2].[t]7.[r][4].Overspeedstatus_Warningstatus (Requirement Type)
t3 >
-p2
- WordTraceId: 211594
- atomic: true
- Legal Obligation: unknown
- PlainText: t3 > -p2
- implement: true
- kind: ordinary

###### 3.13.10.3.4[2].[t]7.[r][5] (Requirement Type)
- WordTraceId: 211620
- atomic: false
- Legal Obligation: not applicable
- implement: false
- kind: Table

###### 3.13.10.3.4[2].[t]7.[r][5].Normalstatus_Interventionstatus (Requirement Type)
t4, t5 >
-p1-
- WordTraceId: 211620
- atomic: true
- Legal Obligation: unknown
- PlainText: t4, t5 > -p1-
- implement: true
- kind: ordinary

###### 3.13.10.3.4[2].[t]7.[r][5].Indicationstatus_Interventionstatus (Requirement Type)
t4, t5 >
-p1-
- WordTraceId: 211634
- atomic: true
- Legal Obligation: unknown
- PlainText: t4, t5 > -p1-
- implement: true
- kind: ordinary

###### 3.13.10.3.4[2].[t]7.[r][5].Overspeedstatus_Interventionstatus (Requirement Type)
t4, t5 >
-p1-
- WordTraceId: 211648
- atomic: true
- Legal Obligation: unknown
- PlainText: t4, t5 > -p1-
- implement: true
- kind: ordinary

###### 3.13.10.3.4[2].[t]7.[r][5].Warningstatus_Interventionstatus (Requirement Type)
t4, t5 >
-p1-
- WordTraceId: 211662
- atomic: true
- Legal Obligation: unknown
- PlainText: t4, t5 > -p1-
- implement: true
- kind: ordinary

###### 3.13.10.3.5 (Requirement Type)
When the speed and distance monitoring function becomes active and the ceiling speed monitoring is the first one entered, the triggering condition t1 defined in Table 5 shall be checked in order to determine whether the Normal status applies. If it is not the case, the on-board shall immediately set the supervision status to the relevant value, applying a transition from the Normal status according to Table 7.
- WordTraceId: 211799
- atomic: false
- Legal Obligation: mandatory
- implement: true
- implementerEnhanced: When
  [CONDITION]
  the speed and distance monitoring function becomes active and the ceiling speed monitoring is the first one entered, the triggering condition t1 defined in Table 5 shall be checked in order to determine
  whether
  [CONDITION]
  the Normal status applies.
  If
  [CONDITION]
  it is not the case, the on-board shall
  immediately
  [WEAK]
  set the supervision status to the relevant value, applying a transition from the Normal status according to Table 7.
- kind: ordinary
- CrossRefLink -> 3.13.10.3.3[2].[t]5.C
- CrossRefLink -> 3.13.10.3.4[2].[t]7.C

###### 3.13.10.3.6 (Requirement Type)
The Indication status is not used in ceiling speed monitoring. However, in case the ceiling speed monitoring is entered and the supervision status was previously set to Indication, the on-board equipment shall immediately execute one of the transitions from the Indication status, as described in Table 7.
- WordTraceId: 212265
- atomic: false
- Legal Obligation: mandatory
- implement: true
- implementerEnhanced: The Indication status is not used in ceiling speed monitoring. However,
  in case
  [CONDITION]
  the ceiling speed monitoring is entered and the supervision status was previously set to Indication, the
  on-board equipment
  [SELF]
  shall
  immediately
  [WEAK]
  execute one of the transitions from the Indication status, as described in Table 7.
- kind: ordinary
- CrossRefLink -> 3.13.10.3.4[2].[t]7.C

###### 3.13.10.3.7 (Requirement Type)
The locations corresponding to a speed increase of the MRSP shall be supervised by the on-board equipment taking into account the min safe front end of the train.
- WordTraceId: 212597
- atomic: true
- Legal Obligation: mandatory
- implement: true
- implementerEnhanced: The locations corresponding to a speed increase of the MRSP shall be supervised by the
  on-board equipment
  [SELF]
  taking into account the min safe front end of the train.
- kind: ordinary

##### 3.13.10.4 (Requirement Type)
Requirements for Target speed monitoring
- WordTraceId: 212760
- atomic: false
- Legal Obligation: not applicable
- implement: false
- kind: Heading

###### 3.13.10.4.1 (Requirement Type)
In target speed monitoring, both the ceiling supervision limits and the braking to target supervision limits, described in sections 3.13.9.2 and 3.13.9.3, are used to determine the commands to the Train Interface and the information displayed to the driver.
- WordTraceId: 212801
- atomic: true
- Legal Obligation: unknown
- implement: true
- implementerEnhanced: In target speed monitoring, both the ceiling supervision limits and the braking to target supervision limits, described in sections 3.13.9.2 and 3.13.9.3, are used to determine the commands to the Train Interface and the information displayed to the
  driver
  [EXTERNAL]
  .
- kind: ordinary
- CrossRefLink -> 3.13.9.2
- CrossRefLink -> 3.13.9.3

###### 3.13.10.4.2 (Requirement Type)
The on-board equipment shall display to the driver the information related to one target at a time: the Most Restrictive Displayed Target (MRDT). The MRDT shall be defined as the target of which the braking to target Permitted speed supervision limit (refer to section 3.13.9.3.5), calculated for the current position of the train, is the lowest one amongst the supervised targets:
- WordTraceId: 213117
- atomic: false
- Legal Obligation: mandatory
- implement: false
- implementerEnhanced: The
  on-board equipment
  [SELF]
  shall display to the
  driver
  [EXTERNAL]
  the information related to one target at a
  time
  [TIME]
  : the Most Restrictive Displayed Target (MRDT). The MRDT shall be defined as the target of which the braking to target Permitted speed supervision limit (refer to section 3.13.9.3.5), calculated for the current position of the train, is the lowest one amongst the supervised targets:
- kind: Definition
- CrossRefLink -> 3.13.9.3.5

###### 3.13.10.4.2[2] (Requirement Type)
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- WordTraceId: 213528
- atomic: true
- Legal Obligation: unknown
- implement: true
- kind: ordinary

###### 3.13.10.4.2[2].1 (Requirement Type)
Once the service brake feedback functionality is active (see Appendix A3.10 for details), the on-board equipment shall ensure that the displayed Permitted speed never increases, if it results from the progressive reduction of T_bs1 and T_bs2. In other terms if the Permitted speed calculated as above has a higher value than the previously displayed value, then the previous value shall remain displayed until a further calculated Permitted speed is lower than the displayed one.
- WordTraceId: 213552
- atomic: false
- Legal Obligation: mandatory
- implement: true
- implementerEnhanced: Once the service brake feedback functionality is active (see Appendix A3.10 for details), the
  on-board equipment
  [SELF]
  shall ensure that the displayed Permitted speed never increases,
  if
  [CONDITION]
  it results from the progressive reduction of T_bs1 and T_bs2. In other terms
  if
  [CONDITION]
  the Permitted speed calculated as
  above
  [WEAK]
  has a higher value than the previously displayed value, then the previous value shall remain displayed
  until
  [TIME]
  a further calculated Permitted speed is lower than the displayed one.
- ListNumberText: 3.13.10.4.2.1
- kind: ordinary
- CrossRefLink -> A.3.10

###### 3.13.10.4.3 (Requirement Type)
The on-board equipment shall display the Permitted speed, according to following formula:
- WordTraceId: 214032
- atomic: true
- Legal Obligation: mandatory
- implement: true
- implementerEnhanced: The
  on-board equipment
  [SELF]
  shall display the Permitted speed, according to following formula:
- kind: ordinary

###### 3.13.10.4.3[2] (Requirement Type)
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- WordTraceId: 214122
- atomic: true
- Legal Obligation: unknown
- implement: true
- kind: ordinary

###### 3.13.10.4.4 (Requirement Type)
When the supervision status is Overspeed, Warning or Intervention, the on-board equipment shall display the FLOI speed, according to the following formulas:
- WordTraceId: 214146
- atomic: true
- Legal Obligation: mandatory
- implement: true
- implementerEnhanced: When
  [CONDITION]
  the supervision status is Overspeed, Warning or Intervention, the
  on-board equipment
  [SELF]
  shall display the FLOI speed, according to the following formulas:
- kind: ordinary

###### 3.13.10.4.4[2] (Requirement Type)
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 in case of MRSP target or LOA
- WordTraceId: 214303
- atomic: true
- Legal Obligation: unknown
- PlainText: in case of MRSP target or LOA
- implement: true
- implementerEnhanced: in case of
  [CONDITION]
  MRSP target or LOA
- kind: ordinary

###### 3.13.10.4.4[3] (Requirement Type)
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 in case of EOA or SvL
- WordTraceId: 214356
- atomic: true
- Legal Obligation: unknown
- PlainText: in case of EOA or SvL
- implement: true
- implementerEnhanced: in case of
  [CONDITION]
  EOA or SvL
- kind: ordinary

###### 3.13.10.4.5 (Requirement Type)
Note: the MRDT is needed to avoid jumps of displayed Permitted speed, when the SBD intersects an EBD or when the target to which the FLOI is related suddenly changes, due to the growth of the train position confidence interval. As a result the MRDT may temporarily not correspond to the target to which the FLOI is related, but this will never be the case when the train speed/location is reaching the supervision limit.
- WordTraceId: 214402
- atomic: false
- Legal Obligation: optional
- implement: false
- implementerEnhanced: Note: the MRDT is needed to avoid jumps of displayed Permitted speed,
  when
  [CONDITION]
  the SBD intersects an EBD or
  when
  [CONDITION]
  the target to which the FLOI is related
  suddenly
  [WEAK]
  changes, due to the growth of the train position confidence interval. As a result the MRDT may
  temporarily
  [WEAK]
  not correspond to the target to which the FLOI is related, but this will never be the case
  when
  [CONDITION]
  the train speed/location is reaching the supervision limit.
- kind: Note

###### 3.13.10.4.6 (Requirement Type)
If the MRDT is either the EOA or the SvL, the on-board equipment shall display the release speed, if given by the trackside or calculated on-board.
- WordTraceId: 214823
- atomic: true
- Legal Obligation: mandatory
- implement: true
- implementerEnhanced: If
  [CONDITION]
  the MRDT is either the EOA or the SvL, the
  on-board equipment
  [SELF]
  shall display the release speed,
  if
  [CONDITION]
  given by the
  trackside
  [EXTERNAL]
  or calculated on-board.
- kind: ordinary

###### 3.13.10.4.7 (Requirement Type)
If the MRDT is neither the EOA nor the SvL, the indicated distance to the target shall be the distance between the maximum safe front end and the location of the Permitted speed supervision limit calculated for the target speed (see section 3.13.9.3.5 for the calculation of this location), but limited to zero after this location is passed.
- WordTraceId: 214971
- atomic: true
- Legal Obligation: mandatory
- implement: true
- implementerEnhanced: If
  [CONDITION]
  the MRDT is neither the EOA nor the SvL, the indicated distance to the target shall be the distance between the maximum safe front end and the location of the Permitted speed supervision limit calculated for the target speed (see section 3.13.9.3.5 for the calculation of this location), but limited to zero
  after
  [TIME]
  this location is passed.
- kind: ordinary
- CrossRefLink -> 3.13.9.3.5

###### 3.13.10.4.7[2] (Requirement Type)
Target distance =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
- WordTraceId: 215342
- atomic: true
- Legal Obligation: unknown
- PlainText: Target distance =
- implement: true
- implementerEnhanced: Target distance =
- kind: ordinary

###### 3.13.10.4.7[2].1 (Requirement Type)
Once the service brake feedback functionality is active (see Appendix A3.10 for details), the on-board equipment shall ensure that the displayed target distance never increases, if it results from the progressive reduction of T_bs1 and T_bs2. In other terms if the target distance calculated as above has a higher value than the previously displayed value, then the previous value shall remain displayed until a further calculated target distance is lower than the displayed one.
- WordTraceId: 215384
- atomic: false
- Legal Obligation: mandatory
- implement: true
- implementerEnhanced: Once the service brake feedback functionality is active (see Appendix A3.10 for details), the
  on-board equipment
  [SELF]
  shall ensure that the displayed target distance never increases,
  if
  [CONDITION]
  it results from the progressive reduction of T_bs1 and T_bs2. In other terms
  if
  [CONDITION]
  the target distance calculated as
  above
  [WEAK]
  has a higher value than the previously displayed value, then the previous value shall remain displayed
  until
  [TIME]
  a further calculated target distance is lower than the displayed one.
- ListNumberText: 3.13.10.4.7.1
- kind: ordinary
- CrossRefLink -> A.3.10

###### 3.13.10.4.8 (Requirement Type)
If the MRDT is either the EOA or the SvL, the indicated distance to the target shall be calculated as follows:
- WordTraceId: 215864
- atomic: true
- Legal Obligation: mandatory
- implement: true
- implementerEnhanced: If
  [CONDITION]
  the MRDT is either the EOA or the SvL, the indicated distance to the target shall be calculated as follows:
- kind: ordinary

###### 3.13.10.4.8[2] (Requirement Type)
Target distance =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
- WordTraceId: 215975
- atomic: true
- Legal Obligation: unknown
- PlainText: Target distance =
- implement: true
- implementerEnhanced: Target distance =
- kind: ordinary

###### 3.13.10.4.9 (Requirement Type)
The on-board shall consider the service brake command as available for use unless:
- WordTraceId: 216017
- atomic: true
- Legal Obligation: mandatory
- implement: true
- kind: ordinary

###### 3.13.10.4.9.a (Requirement Type)
The service brake command is not implemented, OR
- WordTraceId: 216100
- atomic: true
- Legal Obligation: mandatory (== 1)
- implement: true
- ListNumberText: a)
- kind: ordinary

###### 3.13.10.4.9.b (Requirement Type)
The national value inhibits its use.
- WordTraceId: 216149
- atomic: true
- Legal Obligation: mandatory (== 1)
- implement: true
- ListNumberText: b)
- kind: ordinary

###### 3.13.10.4.10 (Requirement Type)
The on-board equipment shall compare the estimated speed and train position with the ceiling and braking to target supervision limits and shall trigger/revoke commands to the train interface (traction cut-off if implemented, service brake if available for use or emergency brake) and supervision statuses, as described in Table 8 and Table 10 (for target related to a MRSP speed decrease or LOA), and as described in Table 9 and Table 11 (for target EOA/SvL with release speed).
- WordTraceId: 216186
- atomic: false
- Legal Obligation: mandatory
- implement: true
- implementerEnhanced: The
  on-board equipment
  [SELF]
  shall compare the estimated speed and train position with the ceiling and braking to target supervision limits and shall trigger/revoke commands to the train interface (traction cut-off
  if
  [CONDITION]
  implemented, service brake
  if
  [CONDITION]
  available for use or emergency brake) and supervision statuses, as described in Table 8 and Table 10 (for target related to a MRSP speed decrease or LOA), and as described in Table 9 and Table 11 (for target EOA/SvL with release speed).
- kind: ordinary
- CrossRefLink -> 3.13.10.4.10[2].[t]8.C
- CrossRefLink -> 3.13.10.4.12[2].[t]10.C
- CrossRefLink -> 3.13.10.4.10[4].[t]9.C
- CrossRefLink -> 3.13.10.4.12[3].[t]11.C

###### 3.13.10.4.10[2] (Requirement Type)
- WordTraceId: 216769
- atomic: false
- Legal Obligation: not applicable
- implement: false
- kind: Placeholder

###### 3.13.10.4.10[2].[t]8 (Requirement Type)
| Triggeringcondition # | Estimated speed | Train front end position (estimated and max safe) | TI Command triggered | Supervision status triggered |
| --- | --- | --- | --- | --- |
| t1 | [C]1.Speed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 | [C]1.Position Not relevant | [C]1.TICommand - | [C]1.Supervision Normal Status |
| t2 | [C]2.Speed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 | [C]2.Position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 if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 OR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if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 | [C]2.TICommand - | [C]2.Supervision Normal Status |
| t3 | [C]2.Speed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 | [C]3.Position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 if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 OR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if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 | [C]3.TICommand - | [C]3.Supervision Indication Status |
| t4 | [C]2.Speed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 | [C]4.Position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 if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 OR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 if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 | [C]4.TICommand - | [C]4.Supervision Overspeed Status |
| t5 | [C]5.Speed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 | [C]5.Position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 if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 OR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if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 | [C]5.TICommand - | [C]5.Supervision Overspeed Status(Pre-indication display area) |
| t6 | [C]5.Speed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 | [C]6.Position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 if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 OR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if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 | [C]6.TICommand - | [C]6.Supervision Overspeed Status |
| t7 | [C]7.Speed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 | [C]7.Position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 if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 OR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if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 | [C]7.TICommand TCO | [C]7.Supervision Warning Status |
| t8 | [C]8.Speed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 | [C]8.Position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 if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 OR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if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 | [C]8.TICommand TCO | [C]8.Supervision Warning Status(Pre-indication display area) |
| t9 | [C]8.Speed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 | [C]9.Position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 if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 OR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if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 | [C]9.TICommand TCO | [C]9.Supervision Warning Status |
| t10 | [C]10.Speed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 | [C]10.Position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 if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 OR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if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 | [C]10.TICommand SB | [C]10.Supervision Intervention Status |
| t11 | [C]11.Speed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 | [C]11.Position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 | [C]11.TICommand SB | [C]11.Supervision Intervention Status(Pre-indication display area) |
| t12 | [C]11.Speed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 | [C]12.Position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 | [C]12.TICommand SB | [C]12.Supervision Intervention Status |
| t13 | [C]13.Speed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 | [C]13.Position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 | [C]13.TICommand EB | [C]13.Supervision Intervention Status |
| t14 | [C]14.Speed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 | [C]14.Position Not relevant | [C]14.TICommand EB | [C]14.Supervision Intervention Status |
- WordTraceId: 218589
- atomic: false
- Legal Obligation: not applicable
- implement: false
- kind: Table

###### 3.13.10.4.10[2].[t]8.C (Requirement Type)
Table {Table 8}: Triggering of Train Interface commands and supervision statuses in target speed monitoring, MRSP target or LOA
- WordTraceId: 218589
- atomic: true
- Legal Obligation: unknown
- PlainText: Table 8: Triggering of Train Interface commands and supervision statuses in target speed monitoring, MRSP target or LOA
- implement: false
- kind: Table

###### 3.13.10.4.10[2].[t]8.[C]1 (Requirement Type)
- WordTraceId: 216908
- atomic: false
- Legal Obligation: not applicable
- implement: false
- kind: Table

###### 3.13.10.4.10[2].[t]8.[C]1.Speed (Requirement Type)
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- WordTraceId: 216911
- atomic: true
- Legal Obligation: unknown
- implement: true
- kind: ordinary

###### 3.13.10.4.10[2].[t]8.[C]1.Position (Requirement Type)
Not relevant
- WordTraceId: 216935
- atomic: true
- Legal Obligation: unknown
- implement: true
- kind: ordinary

###### 3.13.10.4.10[2].[t]8.[C]1.TICommand (Requirement Type)
-
- WordTraceId: 216948
- atomic: true
- Legal Obligation: unknown
- implement: true
- kind: ordinary

###### 3.13.10.4.10[2].[t]8.[C]1.Supervision (Requirement Type)
Normal Status
- WordTraceId: 216950
- atomic: true
- Legal Obligation: unknown
- implement: true
- kind: ordinary

###### 3.13.10.4.10[2].[t]8.[C]2 (Requirement Type)
- WordTraceId: 216966
- atomic: false
- Legal Obligation: not applicable
- implement: false
- kind: Table

###### 3.13.10.4.10[2].[t]8.[C]2.Speed (Requirement Type)
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- WordTraceId: 216969
- atomic: true
- Legal Obligation: unknown
- implement: true
- kind: ordinary

###### 3.13.10.4.10[2].[t]8.[C]2.Position (Requirement Type)
CONTENTS HAVE BEEN SPLIT UP - SEE CHILDREN
- WordTraceId: 216994
- atomic: false
- Legal Obligation: not applicable
- implement: false
- kind: ordinary

###### 3.13.10.4.10[2].[t]8.[C]2.Position.[1] (Requirement Type)
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if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
- WordTraceId: 216994
- atomic: true
- Legal Obligation: unknown
- PlainText: if
- implement: true
- implementerEnhanced: if
  [CONDITION]
- kind: ordinary

###### 3.13.10.4.10[2].[t]8.[C]2.Position.[2] (Requirement Type)
OR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if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
- WordTraceId: 217044
- atomic: true
- Legal Obligation: unknown
- PlainText: OR if
- implement: true
- implementerEnhanced: OR
  if
  [CONDITION]
- kind: ordinary

###### 3.13.10.4.10[2].[t]8.[C]2.TICommand (Requirement Type)
-
- WordTraceId: 217097
- atomic: true
- Legal Obligation: unknown
- implement: true
- kind: ordinary

###### 3.13.10.4.10[2].[t]8.[C]2.Supervision (Requirement Type)
Normal Status
- WordTraceId: 217099
- atomic: true
- Legal Obligation: unknown
- implement: true
- kind: ordinary

###### 3.13.10.4.10[2].[t]8.[C]3 (Requirement Type)
- WordTraceId: 217114
- atomic: false
- Legal Obligation: not applicable
- implement: false
- kind: Table

###### 3.13.10.4.10[2].[t]8.[C]3.Position (Requirement Type)
CONTENTS HAVE BEEN SPLIT UP - SEE CHILDREN
- WordTraceId: 217118
- atomic: false
- Legal Obligation: not applicable
- implement: false
- kind: ordinary

###### 3.13.10.4.10[2].[t]8.[C]3.Position.[1] (Requirement Type)
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if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
- WordTraceId: 217118
- atomic: true
- Legal Obligation: unknown
- PlainText: if
- implement: true
- implementerEnhanced: if
  [CONDITION]
- kind: ordinary

###### 3.13.10.4.10[2].[t]8.[C]3.Position.[2] (Requirement Type)
OR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if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
- WordTraceId: 217168
- atomic: true
- Legal Obligation: unknown
- PlainText: OR if
- implement: true
- implementerEnhanced: OR
  if
  [CONDITION]
- kind: ordinary

###### 3.13.10.4.10[2].[t]8.[C]3.TICommand (Requirement Type)
-
- WordTraceId: 217221
- atomic: true
- Legal Obligation: unknown
- implement: true
- kind: ordinary

###### 3.13.10.4.10[2].[t]8.[C]3.Supervision (Requirement Type)
Indication Status
- WordTraceId: 217223
- atomic: true
- Legal Obligation: unknown
- implement: true
- kind: ordinary

###### 3.13.10.4.10[2].[t]8.[C]4 (Requirement Type)
- WordTraceId: 217242
- atomic: false
- Legal Obligation: not applicable
- implement: false
- kind: Table

###### 3.13.10.4.10[2].[t]8.[C]4.Position (Requirement Type)
CONTENTS HAVE BEEN SPLIT UP - SEE CHILDREN
- WordTraceId: 217246
- atomic: false
- Legal Obligation: not applicable
- implement: false
- kind: ordinary

###### 3.13.10.4.10[2].[t]8.[C]4.Position.[1] (Requirement Type)
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if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
- WordTraceId: 217246
- atomic: true
- Legal Obligation: unknown
- PlainText: if
- implement: true
- implementerEnhanced: if
  [CONDITION]
- kind: ordinary

###### 3.13.10.4.10[2].[t]8.[C]4.Position.[2] (Requirement Type)
OR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 if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
- WordTraceId: 217297
- atomic: true
- Legal Obligation: unknown
- PlainText: OR  if
- implement: true
- implementerEnhanced: OR
  if
  [CONDITION]
- kind: ordinary

###### 3.13.10.4.10[2].[t]8.[C]4.TICommand (Requirement Type)
-
- WordTraceId: 217350
- atomic: true
- Legal Obligation: unknown
- implement: true
- kind: ordinary

###### 3.13.10.4.10[2].[t]8.[C]4.Supervision (Requirement Type)
Overspeed Status
- WordTraceId: 217352
- atomic: true
- Legal Obligation: unknown
- implement: true
- kind: ordinary

###### 3.13.10.4.10[2].[t]8.[C]5 (Requirement Type)
- WordTraceId: 217370
- atomic: false
- Legal Obligation: not applicable
- implement: false
- kind: Table

###### 3.13.10.4.10[2].[t]8.[C]5.Speed (Requirement Type)
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- WordTraceId: 217373
- atomic: true
- Legal Obligation: unknown
- implement: true
- kind: ordinary

###### 3.13.10.4.10[2].[t]8.[C]5.Position (Requirement Type)
CONTENTS HAVE BEEN SPLIT UP - SEE CHILDREN
- WordTraceId: 217397
- atomic: false
- Legal Obligation: not applicable
- implement: false
- kind: ordinary

###### 3.13.10.4.10[2].[t]8.[C]5.Position.[1] (Requirement Type)
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if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
- WordTraceId: 217397
- atomic: true
- Legal Obligation: unknown
- PlainText: if
- implement: true
- implementerEnhanced: if
  [CONDITION]
- kind: ordinary

###### 3.13.10.4.10[2].[t]8.[C]5.Position.[2] (Requirement Type)
OR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if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
- WordTraceId: 217447
- atomic: true
- Legal Obligation: unknown
- PlainText: OR if
- implement: true
- implementerEnhanced: OR
  if
  [CONDITION]
- kind: ordinary

###### 3.13.10.4.10[2].[t]8.[C]5.TICommand (Requirement Type)
-
- WordTraceId: 217500
- atomic: true
- Legal Obligation: unknown
- implement: true
- kind: ordinary

###### 3.13.10.4.10[2].[t]8.[C]5.Supervision (Requirement Type)
Overspeed Status(Pre-indication display area)
- WordTraceId: 217502
- atomic: true
- Legal Obligation: unknown
- implement: true
- kind: ordinary

###### 3.13.10.4.10[2].[t]8.[C]6 (Requirement Type)
- WordTraceId: 217549
- atomic: false
- Legal Obligation: not applicable
- implement: false
- kind: Table

###### 3.13.10.4.10[2].[t]8.[C]6.Position (Requirement Type)
CONTENTS HAVE BEEN SPLIT UP - SEE CHILDREN
- WordTraceId: 217553
- atomic: false
- Legal Obligation: not applicable
- implement: false
- kind: ordinary

###### 3.13.10.4.10[2].[t]8.[C]6.Position.[1] (Requirement Type)
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if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
- WordTraceId: 217553
- atomic: true
- Legal Obligation: unknown
- PlainText: if
- implement: true
- implementerEnhanced: if
  [CONDITION]
- kind: ordinary

###### 3.13.10.4.10[2].[t]8.[C]6.Position.[2] (Requirement Type)
OR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if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
- WordTraceId: 217604
- atomic: true
- Legal Obligation: unknown
- PlainText: OR  if
- implement: true
- implementerEnhanced: OR
  if
  [CONDITION]
- kind: ordinary

###### 3.13.10.4.10[2].[t]8.[C]6.TICommand (Requirement Type)
-
- WordTraceId: 217658
- atomic: true
- Legal Obligation: unknown
- implement: true
- kind: ordinary

###### 3.13.10.4.10[2].[t]8.[C]6.Supervision (Requirement Type)
Overspeed Status
- WordTraceId: 217660
- atomic: true
- Legal Obligation: unknown
- implement: true
- kind: ordinary

###### 3.13.10.4.10[2].[t]8.[C]7 (Requirement Type)
- WordTraceId: 217678
- atomic: false
- Legal Obligation: not applicable
- implement: false
- kind: Table

###### 3.13.10.4.10[2].[t]8.[C]7.Speed (Requirement Type)
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- WordTraceId: 217681
- atomic: true
- Legal Obligation: unknown
- implement: true
- kind: ordinary

###### 3.13.10.4.10[2].[t]8.[C]7.Position (Requirement Type)
CONTENTS HAVE BEEN SPLIT UP - SEE CHILDREN
- WordTraceId: 217705
- atomic: false
- Legal Obligation: not applicable
- implement: false
- kind: ordinary

###### 3.13.10.4.10[2].[t]8.[C]7.Position.[1] (Requirement Type)
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if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
- WordTraceId: 217705
- atomic: true
- Legal Obligation: unknown
- PlainText: if
- implement: true
- implementerEnhanced: if
  [CONDITION]
- kind: ordinary

###### 3.13.10.4.10[2].[t]8.[C]7.Position.[2] (Requirement Type)
OR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if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
- WordTraceId: 217755
- atomic: true
- Legal Obligation: unknown
- PlainText: OR if
- implement: true
- implementerEnhanced: OR
  if
  [CONDITION]
- kind: ordinary

###### 3.13.10.4.10[2].[t]8.[C]7.TICommand (Requirement Type)
TCO
- WordTraceId: 217808
- atomic: true
- Legal Obligation: unknown
- implement: true
- kind: ordinary

###### 3.13.10.4.10[2].[t]8.[C]7.Supervision (Requirement Type)
Warning Status
- WordTraceId: 217812
- atomic: true
- Legal Obligation: unknown
- implement: true
- kind: ordinary

###### 3.13.10.4.10[2].[t]8.[C]8 (Requirement Type)
- WordTraceId: 217828
- atomic: false
- Legal Obligation: not applicable
- implement: false
- kind: Table

###### 3.13.10.4.10[2].[t]8.[C]8.Speed (Requirement Type)
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- WordTraceId: 217831
- atomic: true
- Legal Obligation: unknown
- implement: true
- kind: ordinary

###### 3.13.10.4.10[2].[t]8.[C]8.Position (Requirement Type)
CONTENTS HAVE BEEN SPLIT UP - SEE CHILDREN
- WordTraceId: 217855
- atomic: false
- Legal Obligation: not applicable
- implement: false
- kind: ordinary

###### 3.13.10.4.10[2].[t]8.[C]8.Position.[1] (Requirement Type)
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if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
- WordTraceId: 217855
- atomic: true
- Legal Obligation: unknown
- PlainText: if
- implement: true
- implementerEnhanced: if
  [CONDITION]
- kind: ordinary

###### 3.13.10.4.10[2].[t]8.[C]8.Position.[2] (Requirement Type)
OR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if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
- WordTraceId: 217905
- atomic: true
- Legal Obligation: unknown
- PlainText: OR if
- implement: true
- implementerEnhanced: OR
  if
  [CONDITION]
- kind: ordinary

###### 3.13.10.4.10[2].[t]8.[C]8.TICommand (Requirement Type)
TCO
- WordTraceId: 217958
- atomic: true
- Legal Obligation: unknown
- implement: true
- kind: ordinary

###### 3.13.10.4.10[2].[t]8.[C]8.Supervision (Requirement Type)
Warning Status(Pre-indication display area)
- WordTraceId: 217962
- atomic: true
- Legal Obligation: unknown
- implement: true
- kind: ordinary

###### 3.13.10.4.10[2].[t]8.[C]9 (Requirement Type)
- WordTraceId: 218007
- atomic: false
- Legal Obligation: not applicable
- implement: false
- kind: Table

###### 3.13.10.4.10[2].[t]8.[C]9.Position (Requirement Type)
CONTENTS HAVE BEEN SPLIT UP - SEE CHILDREN
- WordTraceId: 218011
- atomic: false
- Legal Obligation: not applicable
- implement: false
- kind: ordinary

###### 3.13.10.4.10[2].[t]8.[C]9.Position.[1] (Requirement Type)
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if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
- WordTraceId: 218011
- atomic: true
- Legal Obligation: unknown
- PlainText: if
- implement: true
- implementerEnhanced: if
  [CONDITION]
- kind: ordinary

###### 3.13.10.4.10[2].[t]8.[C]9.Position.[2] (Requirement Type)
OR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if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
- WordTraceId: 218062
- atomic: true
- Legal Obligation: unknown
- PlainText: OR  if
- implement: true
- implementerEnhanced: OR
  if
  [CONDITION]
- kind: ordinary

###### 3.13.10.4.10[2].[t]8.[C]9.TICommand (Requirement Type)
TCO
- WordTraceId: 218116
- atomic: true
- Legal Obligation: unknown
- implement: true
- kind: ordinary

###### 3.13.10.4.10[2].[t]8.[C]9.Supervision (Requirement Type)
Warning Status
- WordTraceId: 218120
- atomic: true
- Legal Obligation: unknown
- implement: true
- kind: ordinary

###### 3.13.10.4.10[2].[t]8.[C]10 (Requirement Type)
- WordTraceId: 218136
- atomic: false
- Legal Obligation: not applicable
- implement: false
- kind: Table

###### 3.13.10.4.10[2].[t]8.[C]10.Speed (Requirement Type)
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- WordTraceId: 218140
- atomic: true
- Legal Obligation: unknown
- implement: true
- kind: ordinary

###### 3.13.10.4.10[2].[t]8.[C]10.Position (Requirement Type)
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if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 OR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if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
- WordTraceId: 218164
- atomic: true
- Legal Obligation: unknown
- PlainText: if OR if
- implement: true
- implementerEnhanced: if
  [CONDITION]
  OR
  if
  [CONDITION]
- kind: ordinary

###### 3.13.10.4.10[2].[t]8.[C]10.TICommand (Requirement Type)
SB
- WordTraceId: 218266
- atomic: true
- Legal Obligation: unknown
- implement: true
- kind: ordinary

###### 3.13.10.4.10[2].[t]8.[C]10.Supervision (Requirement Type)
Intervention Status
- WordTraceId: 218269
- atomic: true
- Legal Obligation: unknown
- implement: true
- kind: ordinary

###### 3.13.10.4.10[2].[t]8.[C]11 (Requirement Type)
- WordTraceId: 218290
- atomic: false
- Legal Obligation: not applicable
- implement: false
- kind: Table

###### 3.13.10.4.10[2].[t]8.[C]11.Speed (Requirement Type)
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- WordTraceId: 218294
- atomic: true
- Legal Obligation: unknown
- implement: true
- kind: ordinary

###### 3.13.10.4.10[2].[t]8.[C]11.Position (Requirement Type)
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- WordTraceId: 218318
- atomic: true
- Legal Obligation: unknown
- implement: true
- kind: ordinary

###### 3.13.10.4.10[2].[t]8.[C]11.TICommand (Requirement Type)
SB
- WordTraceId: 218342
- atomic: true
- Legal Obligation: unknown
- implement: true
- kind: ordinary

###### 3.13.10.4.10[2].[t]8.[C]11.Supervision (Requirement Type)
Intervention Status(Pre-indication display area)
- WordTraceId: 218345
- atomic: true
- Legal Obligation: unknown
- implement: true
- kind: ordinary

###### 3.13.10.4.10[2].[t]8.[C]12 (Requirement Type)
- WordTraceId: 218395
- atomic: false
- Legal Obligation: not applicable
- implement: false
- kind: Table

###### 3.13.10.4.10[2].[t]8.[C]12.Position (Requirement Type)
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- WordTraceId: 218400
- atomic: true
- Legal Obligation: unknown
- implement: true
- kind: ordinary

###### 3.13.10.4.10[2].[t]8.[C]12.TICommand (Requirement Type)
SB
- WordTraceId: 218424
- atomic: true
- Legal Obligation: unknown
- implement: true
- kind: ordinary

###### 3.13.10.4.10[2].[t]8.[C]12.Supervision (Requirement Type)
Intervention Status
- WordTraceId: 218427
- atomic: true
- Legal Obligation: unknown
- implement: true
- kind: ordinary

###### 3.13.10.4.10[2].[t]8.[C]13 (Requirement Type)
- WordTraceId: 218448
- atomic: false
- Legal Obligation: not applicable
- implement: false
- kind: Table

###### 3.13.10.4.10[2].[t]8.[C]13.Speed (Requirement Type)
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- WordTraceId: 218452
- atomic: true
- Legal Obligation: unknown
- implement: true
- kind: ordinary

###### 3.13.10.4.10[2].[t]8.[C]13.Position (Requirement Type)
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- WordTraceId: 218476
- atomic: true
- Legal Obligation: unknown
- implement: true
- kind: ordinary

###### 3.13.10.4.10[2].[t]8.[C]13.TICommand (Requirement Type)
EB
- WordTraceId: 218500
- atomic: true
- Legal Obligation: unknown
- implement: true
- kind: ordinary

###### 3.13.10.4.10[2].[t]8.[C]13.Supervision (Requirement Type)
Intervention Status
- WordTraceId: 218503
- atomic: true
- Legal Obligation: unknown
- implement: true
- kind: ordinary

###### 3.13.10.4.10[2].[t]8.[C]14 (Requirement Type)
- WordTraceId: 218524
- atomic: false
- Legal Obligation: not applicable
- implement: false
- kind: Table

###### 3.13.10.4.10[2].[t]8.[C]14.Speed (Requirement Type)
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- WordTraceId: 218528
- atomic: true
- Legal Obligation: unknown
- implement: true
- kind: ordinary

###### 3.13.10.4.10[2].[t]8.[C]14.Position (Requirement Type)
Not relevant
- WordTraceId: 218552
- atomic: true
- Legal Obligation: unknown
- implement: true
- kind: ordinary

###### 3.13.10.4.10[2].[t]8.[C]14.TICommand (Requirement Type)
EB
- WordTraceId: 218565
- atomic: true
- Legal Obligation: unknown
- implement: true
- kind: ordinary

###### 3.13.10.4.10[2].[t]8.[C]14.Supervision (Requirement Type)
Intervention Status
- WordTraceId: 218568
- atomic: true
- Legal Obligation: unknown
- implement: true
- kind: ordinary

###### 3.13.10.4.10[3] (Requirement Type)
- WordTraceId: 218733
- atomic: false
- Legal Obligation: not applicable
- implement: false
- kind: Placeholder

###### 3.13.10.4.10[3].[f]55 (Requirement Type)
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- WordTraceId: 218761
- atomic: false
- Legal Obligation: not applicable
- implement: false
- kind: Figure

###### 3.13.10.4.10[3].[f]55.C (Requirement Type)
Figure {Figure 55}: Triggering of Train Interface commands and supervision statuses in target speed monitoring, MRSP target or LOA (number in circle corresponds with the equivalent triggering condition in Table 8)
- WordTraceId: 218761
- atomic: true
- Legal Obligation: unknown
- PlainText: Figure 55: Triggering of Train Interface commands and supervision statuses in target speed monitoring, MRSP target or LOA (number in circle corresponds with the equivalent triggering condition in Table 8)
- implement: false
- kind: Figure

###### 3.13.10.4.10[4] (Requirement Type)
- WordTraceId: 219017
- atomic: false
- Legal Obligation: not applicable
- implement: false
- kind: Placeholder

###### 3.13.10.4.10[4].[t]9 (Requirement Type)
| Triggeringcondition # | Estimated speed | Train front end position (estimated and max safe) | TI Command triggered | Supervision status triggered |
| --- | --- | --- | --- | --- |
| t1 | [C]1.Speed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 | [C]1.Position Not relevant | [C]1.TICommand - | [C]1.Supervision Normal Status |
| t2 | [C]2.Speed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 | [C]2.Position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 if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 OR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if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 | [C]2.TICommand - | [C]2.Supervision Normal Status |
| t3 | [C]2.Speed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 | [C]3.Position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 if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 OR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if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 | [C]3.TICommand | [C]3.Supervision Indication Status |
| t4 | [C]2.Speed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 | [C]4.Position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 if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 OR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 if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 | [C]4.TICommand | [C]4.Supervision Overspeed Status |
| t5 | [C]5.Speed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 | [C]5.Position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 if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 OR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if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 | [C]5.TICommand - | [C]5.Supervision Overspeed Status(Pre-indication display area) |
| t6 | [C]5.Speed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 | [C]6.Position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 if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 OR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if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 | [C]6.TICommand - | [C]6.Supervision Overspeed Status |
| t7 | [C]7.Speed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 | [C]7.Position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 if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 OR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if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 | [C]7.TICommand TCO | [C]7.Supervision Warning Status |
| t8 | [C]8.Speed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 | [C]8.Position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 if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 OR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if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 | [C]8.TICommand TCO | [C]8.Supervision Warning Status(Pre-indication display area) |
| t9 | [C]8.Speed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 | [C]9.Position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 if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 OR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if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 | [C]9.TICommand TCO | [C]9.Supervision Warning Status |
| t10 | [C]10.Speed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 | [C]10.Position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 if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 OR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if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 | [C]10.TICommand SB | [C]10.Supervision Intervention Status |
| t11 | [C]11.Speed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 | [C]11.Position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 | [C]11.TICommand SB | [C]11.Supervision Intervention Status(Pre-indication display area) |
| t12 | [C]11.Speed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 | [C]12.Position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 | [C]12.TICommand SB | [C]12.Supervision Intervention Status |
| t13 | [C]13.Speed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 | [C]13.Position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 | [C]13.TICommand EB | [C]13.Supervision Intervention Status |
| t14 | [C]14.Speed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 | [C]14.Position Not relevant | [C]14.TICommand EB | [C]14.Supervision Intervention Status |
- WordTraceId: 220833
- atomic: false
- Legal Obligation: not applicable
- implement: false
- kind: Table

###### 3.13.10.4.10[4].[t]9.C (Requirement Type)
Table {Table 9}: Triggering of Train Interface commands and supervision statuses in target speed monitoring, EOA/SvL with release speed
- WordTraceId: 220833
- atomic: true
- Legal Obligation: unknown
- PlainText: Table 9: Triggering of Train Interface commands and supervision statuses in target speed monitoring, EOA/SvL with release speed
- implement: false
- kind: Table

###### 3.13.10.4.10[4].[t]9.[C]1 (Requirement Type)
- WordTraceId: 219156
- atomic: false
- Legal Obligation: not applicable
- implement: false
- kind: Table

###### 3.13.10.4.10[4].[t]9.[C]1.Speed (Requirement Type)
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- WordTraceId: 219159
- atomic: true
- Legal Obligation: unknown
- implement: true
- kind: ordinary

###### 3.13.10.4.10[4].[t]9.[C]1.Position (Requirement Type)
Not relevant
- WordTraceId: 219183
- atomic: true
- Legal Obligation: unknown
- implement: true
- kind: ordinary

###### 3.13.10.4.10[4].[t]9.[C]1.TICommand (Requirement Type)
-
- WordTraceId: 219196
- atomic: true
- Legal Obligation: unknown
- implement: true
- kind: ordinary

###### 3.13.10.4.10[4].[t]9.[C]1.Supervision (Requirement Type)
Normal Status
- WordTraceId: 219198
- atomic: true
- Legal Obligation: unknown
- implement: true
- kind: ordinary

###### 3.13.10.4.10[4].[t]9.[C]2 (Requirement Type)
- WordTraceId: 219213
- atomic: false
- Legal Obligation: not applicable
- implement: false
- kind: Table

###### 3.13.10.4.10[4].[t]9.[C]2.Speed (Requirement Type)
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- WordTraceId: 219216
- atomic: true
- Legal Obligation: unknown
- implement: true
- kind: ordinary

###### 3.13.10.4.10[4].[t]9.[C]2.Position (Requirement Type)
CONTENTS HAVE BEEN SPLIT UP - SEE CHILDREN
- WordTraceId: 219240
- atomic: false
- Legal Obligation: not applicable
- implement: false
- kind: ordinary

###### 3.13.10.4.10[4].[t]9.[C]2.Position.[1] (Requirement Type)
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if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
- WordTraceId: 219240
- atomic: true
- Legal Obligation: unknown
- PlainText: if
- implement: true
- implementerEnhanced: if
  [CONDITION]
- kind: ordinary

###### 3.13.10.4.10[4].[t]9.[C]2.Position.[2] (Requirement Type)
OR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if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
- WordTraceId: 219290
- atomic: true
- Legal Obligation: unknown
- PlainText: OR if
- implement: true
- implementerEnhanced: OR
  if
  [CONDITION]
- kind: ordinary

###### 3.13.10.4.10[4].[t]9.[C]2.TICommand (Requirement Type)
-
- WordTraceId: 219343
- atomic: true
- Legal Obligation: unknown
- implement: true
- kind: ordinary

###### 3.13.10.4.10[4].[t]9.[C]2.Supervision (Requirement Type)
Normal Status
- WordTraceId: 219345
- atomic: true
- Legal Obligation: unknown
- implement: true
- kind: ordinary

###### 3.13.10.4.10[4].[t]9.[C]3 (Requirement Type)
- WordTraceId: 219360
- atomic: false
- Legal Obligation: not applicable
- implement: false
- kind: Table

###### 3.13.10.4.10[4].[t]9.[C]3.Position (Requirement Type)
CONTENTS HAVE BEEN SPLIT UP - SEE CHILDREN
- WordTraceId: 219364
- atomic: false
- Legal Obligation: not applicable
- implement: false
- kind: ordinary

###### 3.13.10.4.10[4].[t]9.[C]3.Position.[1] (Requirement Type)
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if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
- WordTraceId: 219364
- atomic: true
- Legal Obligation: unknown
- PlainText: if
- implement: true
- implementerEnhanced: if
  [CONDITION]
- kind: ordinary

###### 3.13.10.4.10[4].[t]9.[C]3.Position.[2] (Requirement Type)
OR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if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
- WordTraceId: 219414
- atomic: true
- Legal Obligation: unknown
- PlainText: OR if
- implement: true
- implementerEnhanced: OR
  if
  [CONDITION]
- kind: ordinary

###### 3.13.10.4.10[4].[t]9.[C]3.TICommand (Requirement Type)
- WordTraceId: 219467
- atomic: true
- Legal Obligation: unknown
- implement: true
- kind: ordinary

###### 3.13.10.4.10[4].[t]9.[C]3.Supervision (Requirement Type)
Indication Status
- WordTraceId: 219468
- atomic: true
- Legal Obligation: unknown
- implement: true
- kind: ordinary

###### 3.13.10.4.10[4].[t]9.[C]4 (Requirement Type)
- WordTraceId: 219487
- atomic: false
- Legal Obligation: not applicable
- implement: false
- kind: Table

###### 3.13.10.4.10[4].[t]9.[C]4.Position (Requirement Type)
CONTENTS HAVE BEEN SPLIT UP - SEE CHILDREN
- WordTraceId: 219491
- atomic: false
- Legal Obligation: not applicable
- implement: false
- kind: ordinary

###### 3.13.10.4.10[4].[t]9.[C]4.Position.[1] (Requirement Type)
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if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
- WordTraceId: 219491
- atomic: true
- Legal Obligation: unknown
- PlainText: if
- implement: true
- implementerEnhanced: if
  [CONDITION]
- kind: ordinary

###### 3.13.10.4.10[4].[t]9.[C]4.Position.[2] (Requirement Type)
OR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 if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
- WordTraceId: 219542
- atomic: true
- Legal Obligation: unknown
- PlainText: OR  if
- implement: true
- implementerEnhanced: OR
  if
  [CONDITION]
- kind: ordinary

###### 3.13.10.4.10[4].[t]9.[C]4.TICommand (Requirement Type)
- WordTraceId: 219595
- atomic: true
- Legal Obligation: unknown
- implement: true
- kind: ordinary

###### 3.13.10.4.10[4].[t]9.[C]4.Supervision (Requirement Type)
Overspeed Status
- WordTraceId: 219596
- atomic: true
- Legal Obligation: unknown
- implement: true
- kind: ordinary

###### 3.13.10.4.10[4].[t]9.[C]5 (Requirement Type)
- WordTraceId: 219614
- atomic: false
- Legal Obligation: not applicable
- implement: false
- kind: Table

###### 3.13.10.4.10[4].[t]9.[C]5.Speed (Requirement Type)
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- WordTraceId: 219617
- atomic: true
- Legal Obligation: unknown
- implement: true
- kind: ordinary

###### 3.13.10.4.10[4].[t]9.[C]5.Position (Requirement Type)
CONTENTS HAVE BEEN SPLIT UP - SEE CHILDREN
- WordTraceId: 219641
- atomic: false
- Legal Obligation: not applicable
- implement: false
- kind: ordinary

###### 3.13.10.4.10[4].[t]9.[C]5.Position.[1] (Requirement Type)
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if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
- WordTraceId: 219641
- atomic: true
- Legal Obligation: unknown
- PlainText: if
- implement: true
- implementerEnhanced: if
  [CONDITION]
- kind: ordinary

###### 3.13.10.4.10[4].[t]9.[C]5.Position.[2] (Requirement Type)
OR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if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
- WordTraceId: 219691
- atomic: true
- Legal Obligation: unknown
- PlainText: OR if
- implement: true
- implementerEnhanced: OR
  if
  [CONDITION]
- kind: ordinary

###### 3.13.10.4.10[4].[t]9.[C]5.TICommand (Requirement Type)
-
- WordTraceId: 219744
- atomic: true
- Legal Obligation: unknown
- implement: true
- kind: ordinary

###### 3.13.10.4.10[4].[t]9.[C]5.Supervision (Requirement Type)
Overspeed Status(Pre-indication display area)
- WordTraceId: 219746
- atomic: true
- Legal Obligation: unknown
- implement: true
- kind: ordinary

###### 3.13.10.4.10[4].[t]9.[C]6 (Requirement Type)
- WordTraceId: 219793
- atomic: false
- Legal Obligation: not applicable
- implement: false
- kind: Table

###### 3.13.10.4.10[4].[t]9.[C]6.Position (Requirement Type)
CONTENTS HAVE BEEN SPLIT UP - SEE CHILDREN
- WordTraceId: 219797
- atomic: false
- Legal Obligation: not applicable
- implement: false
- kind: ordinary

###### 3.13.10.4.10[4].[t]9.[C]6.Position.[1] (Requirement Type)
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if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
- WordTraceId: 219797
- atomic: true
- Legal Obligation: unknown
- PlainText: if
- implement: true
- implementerEnhanced: if
  [CONDITION]
- kind: ordinary

###### 3.13.10.4.10[4].[t]9.[C]6.Position.[2] (Requirement Type)
OR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if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
- WordTraceId: 219848
- atomic: true
- Legal Obligation: unknown
- PlainText: OR  if
- implement: true
- implementerEnhanced: OR
  if
  [CONDITION]
- kind: ordinary

###### 3.13.10.4.10[4].[t]9.[C]6.TICommand (Requirement Type)
-
- WordTraceId: 219902
- atomic: true
- Legal Obligation: unknown
- implement: true
- kind: ordinary

###### 3.13.10.4.10[4].[t]9.[C]6.Supervision (Requirement Type)
Overspeed Status
- WordTraceId: 219904
- atomic: true
- Legal Obligation: unknown
- implement: true
- kind: ordinary

###### 3.13.10.4.10[4].[t]9.[C]7 (Requirement Type)
- WordTraceId: 219922
- atomic: false
- Legal Obligation: not applicable
- implement: false
- kind: Table

###### 3.13.10.4.10[4].[t]9.[C]7.Speed (Requirement Type)
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- WordTraceId: 219925
- atomic: true
- Legal Obligation: unknown
- implement: true
- kind: ordinary

###### 3.13.10.4.10[4].[t]9.[C]7.Position (Requirement Type)
CONTENTS HAVE BEEN SPLIT UP - SEE CHILDREN
- WordTraceId: 219949
- atomic: false
- Legal Obligation: not applicable
- implement: false
- kind: ordinary

###### 3.13.10.4.10[4].[t]9.[C]7.Position.[1] (Requirement Type)
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if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
- WordTraceId: 219949
- atomic: true
- Legal Obligation: unknown
- PlainText: if
- implement: true
- implementerEnhanced: if
  [CONDITION]
- kind: ordinary

###### 3.13.10.4.10[4].[t]9.[C]7.Position.[2] (Requirement Type)
OR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if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
- WordTraceId: 219999
- atomic: true
- Legal Obligation: unknown
- PlainText: OR if
- implement: true
- implementerEnhanced: OR
  if
  [CONDITION]
- kind: ordinary

###### 3.13.10.4.10[4].[t]9.[C]7.TICommand (Requirement Type)
TCO
- WordTraceId: 220052
- atomic: true
- Legal Obligation: unknown
- implement: true
- kind: ordinary

###### 3.13.10.4.10[4].[t]9.[C]7.Supervision (Requirement Type)
Warning Status
- WordTraceId: 220056
- atomic: true
- Legal Obligation: unknown
- implement: true
- kind: ordinary

###### 3.13.10.4.10[4].[t]9.[C]8 (Requirement Type)
- WordTraceId: 220072
- atomic: false
- Legal Obligation: not applicable
- implement: false
- kind: Table

###### 3.13.10.4.10[4].[t]9.[C]8.Speed (Requirement Type)
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- WordTraceId: 220075
- atomic: true
- Legal Obligation: unknown
- implement: true
- kind: ordinary

###### 3.13.10.4.10[4].[t]9.[C]8.Position (Requirement Type)
CONTENTS HAVE BEEN SPLIT UP - SEE CHILDREN
- WordTraceId: 220099
- atomic: false
- Legal Obligation: not applicable
- implement: false
- kind: ordinary

###### 3.13.10.4.10[4].[t]9.[C]8.Position.[1] (Requirement Type)
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if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
- WordTraceId: 220099
- atomic: true
- Legal Obligation: unknown
- PlainText: if
- implement: true
- implementerEnhanced: if
  [CONDITION]
- kind: ordinary

###### 3.13.10.4.10[4].[t]9.[C]8.Position.[2] (Requirement Type)
OR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if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
- WordTraceId: 220149
- atomic: true
- Legal Obligation: unknown
- PlainText: OR if
- implement: true
- implementerEnhanced: OR
  if
  [CONDITION]
- kind: ordinary

###### 3.13.10.4.10[4].[t]9.[C]8.TICommand (Requirement Type)
TCO
- WordTraceId: 220202
- atomic: true
- Legal Obligation: unknown
- implement: true
- kind: ordinary

###### 3.13.10.4.10[4].[t]9.[C]8.Supervision (Requirement Type)
Warning Status(Pre-indication display area)
- WordTraceId: 220206
- atomic: true
- Legal Obligation: unknown
- implement: true
- kind: ordinary

###### 3.13.10.4.10[4].[t]9.[C]9 (Requirement Type)
- WordTraceId: 220251
- atomic: false
- Legal Obligation: not applicable
- implement: false
- kind: Table

###### 3.13.10.4.10[4].[t]9.[C]9.Position (Requirement Type)
CONTENTS HAVE BEEN SPLIT UP - SEE CHILDREN
- WordTraceId: 220255
- atomic: false
- Legal Obligation: not applicable
- implement: false
- kind: ordinary

###### 3.13.10.4.10[4].[t]9.[C]9.Position.[1] (Requirement Type)
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if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
- WordTraceId: 220255
- atomic: true
- Legal Obligation: unknown
- PlainText: if
- implement: true
- implementerEnhanced: if
  [CONDITION]
- kind: ordinary

###### 3.13.10.4.10[4].[t]9.[C]9.Position.[2] (Requirement Type)
OR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if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
- WordTraceId: 220306
- atomic: true
- Legal Obligation: unknown
- PlainText: OR  if
- implement: true
- implementerEnhanced: OR
  if
  [CONDITION]
- kind: ordinary

###### 3.13.10.4.10[4].[t]9.[C]9.TICommand (Requirement Type)
TCO
- WordTraceId: 220360
- atomic: true
- Legal Obligation: unknown
- implement: true
- kind: ordinary

###### 3.13.10.4.10[4].[t]9.[C]9.Supervision (Requirement Type)
Warning Status
- WordTraceId: 220364
- atomic: true
- Legal Obligation: unknown
- implement: true
- kind: ordinary

###### 3.13.10.4.10[4].[t]9.[C]10 (Requirement Type)
- WordTraceId: 220380
- atomic: false
- Legal Obligation: not applicable
- implement: false
- kind: Table

###### 3.13.10.4.10[4].[t]9.[C]10.Speed (Requirement Type)
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- WordTraceId: 220384
- atomic: true
- Legal Obligation: unknown
- implement: true
- kind: ordinary

###### 3.13.10.4.10[4].[t]9.[C]10.Position (Requirement Type)
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if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 OR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if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
- WordTraceId: 220408
- atomic: true
- Legal Obligation: unknown
- PlainText: if OR if
- implement: true
- implementerEnhanced: if
  [CONDITION]
  OR
  if
  [CONDITION]
- kind: ordinary

###### 3.13.10.4.10[4].[t]9.[C]10.TICommand (Requirement Type)
SB
- WordTraceId: 220510
- atomic: true
- Legal Obligation: unknown
- implement: true
- kind: ordinary

###### 3.13.10.4.10[4].[t]9.[C]10.Supervision (Requirement Type)
Intervention Status
- WordTraceId: 220513
- atomic: true
- Legal Obligation: unknown
- implement: true
- kind: ordinary

###### 3.13.10.4.10[4].[t]9.[C]11 (Requirement Type)
- WordTraceId: 220534
- atomic: false
- Legal Obligation: not applicable
- implement: false
- kind: Table

###### 3.13.10.4.10[4].[t]9.[C]11.Speed (Requirement Type)
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- WordTraceId: 220538
- atomic: true
- Legal Obligation: unknown
- implement: true
- kind: ordinary

###### 3.13.10.4.10[4].[t]9.[C]11.Position (Requirement Type)
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- WordTraceId: 220562
- atomic: true
- Legal Obligation: unknown
- implement: true
- kind: ordinary

###### 3.13.10.4.10[4].[t]9.[C]11.TICommand (Requirement Type)
SB
- WordTraceId: 220586
- atomic: true
- Legal Obligation: unknown
- implement: true
- kind: ordinary

###### 3.13.10.4.10[4].[t]9.[C]11.Supervision (Requirement Type)
Intervention Status(Pre-indication display area)
- WordTraceId: 220589
- atomic: true
- Legal Obligation: unknown
- implement: true
- kind: ordinary

###### 3.13.10.4.10[4].[t]9.[C]12 (Requirement Type)
- WordTraceId: 220639
- atomic: false
- Legal Obligation: not applicable
- implement: false
- kind: Table

###### 3.13.10.4.10[4].[t]9.[C]12.Position (Requirement Type)
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- WordTraceId: 220644
- atomic: true
- Legal Obligation: unknown
- implement: true
- kind: ordinary

###### 3.13.10.4.10[4].[t]9.[C]12.TICommand (Requirement Type)
SB
- WordTraceId: 220668
- atomic: true
- Legal Obligation: unknown
- implement: true
- kind: ordinary

###### 3.13.10.4.10[4].[t]9.[C]12.Supervision (Requirement Type)
Intervention Status
- WordTraceId: 220671
- atomic: true
- Legal Obligation: unknown
- implement: true
- kind: ordinary

###### 3.13.10.4.10[4].[t]9.[C]13 (Requirement Type)
- WordTraceId: 220692
- atomic: false
- Legal Obligation: not applicable
- implement: false
- kind: Table

###### 3.13.10.4.10[4].[t]9.[C]13.Speed (Requirement Type)
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- WordTraceId: 220696
- atomic: true
- Legal Obligation: unknown
- implement: true
- kind: ordinary

###### 3.13.10.4.10[4].[t]9.[C]13.Position (Requirement Type)
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- WordTraceId: 220720
- atomic: true
- Legal Obligation: unknown
- implement: true
- kind: ordinary

###### 3.13.10.4.10[4].[t]9.[C]13.TICommand (Requirement Type)
EB
- WordTraceId: 220744
- atomic: true
- Legal Obligation: unknown
- implement: true
- kind: ordinary

###### 3.13.10.4.10[4].[t]9.[C]13.Supervision (Requirement Type)
Intervention Status
- WordTraceId: 220747
- atomic: true
- Legal Obligation: unknown
- implement: true
- kind: ordinary

###### 3.13.10.4.10[4].[t]9.[C]14 (Requirement Type)
- WordTraceId: 220768
- atomic: false
- Legal Obligation: not applicable
- implement: false
- kind: Table

###### 3.13.10.4.10[4].[t]9.[C]14.Speed (Requirement Type)
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- WordTraceId: 220772
- atomic: true
- Legal Obligation: unknown
- implement: true
- kind: ordinary

###### 3.13.10.4.10[4].[t]9.[C]14.Position (Requirement Type)
Not relevant
- WordTraceId: 220796
- atomic: true
- Legal Obligation: unknown
- implement: true
- kind: ordinary

###### 3.13.10.4.10[4].[t]9.[C]14.TICommand (Requirement Type)
EB
- WordTraceId: 220809
- atomic: true
- Legal Obligation: unknown
- implement: true
- kind: ordinary

###### 3.13.10.4.10[4].[t]9.[C]14.Supervision (Requirement Type)
Intervention Status
- WordTraceId: 220812
- atomic: true
- Legal Obligation: unknown
- implement: true
- kind: ordinary

###### 3.13.10.4.10[5] (Requirement Type)
- WordTraceId: 220985
- atomic: false
- Legal Obligation: not applicable
- implement: false
- kind: Placeholder

###### 3.13.10.4.10[5].[f]56 (Requirement Type)
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- WordTraceId: 221013
- atomic: false
- Legal Obligation: not applicable
- implement: false
- kind: Figure

###### 3.13.10.4.10[5].[f]56.C (Requirement Type)
Figure {Figure 56}: Triggering of Train Interface commands and supervision statuses in target speed monitoring, EOA/SvL with release speed (number in circle corresponds with equivalent triggering condition in Table 9)
- WordTraceId: 221013
- atomic: true
- Legal Obligation: unknown
- PlainText: Figure 56: Triggering of Train Interface commands and supervision statuses in target speed monitoring, EOA/SvL with release speed (number in circle corresponds with equivalent triggering condition in Table 9)
- implement: false
- kind: Figure

###### 3.13.10.4.11 (Requirement Type)
The braking to target Indication supervision limit is not used for estimated speeds higher than V_MRSP. However the location of the Indication supervision limit, valid for V_MRSP, when used to derive the pre-indication location of the target, shall be used for estimated speeds higher than V_MRSP in order to discriminate whether information related to the Indication status has to be displayed to the driver. In other terms, for estimated speeds above V_MRSP, the Indication supervision limit is a fixed location, which defines a pre-indication display area starting from the pre-indication location and ending to this fixed location.
- WordTraceId: 221273
- atomic: false
- Legal Obligation: mandatory
- implement: false
- implementerEnhanced: The braking to target Indication supervision limit is not used for estimated speeds higher than V_MRSP. However the location of the Indication supervision limit, valid for V_MRSP,
  when
  [CONDITION]
  used to derive the pre-indication location of the target, shall be used for estimated speeds higher than V_MRSP in order to discriminate
  whether
  [CONDITION]
  information related to the Indication status has to be displayed to the
  driver
  [EXTERNAL]
  . In other terms, for estimated speeds
  above
  [WEAK]
  V_MRSP, the Indication supervision limit is a fixed location, which defines a pre-indication display area starting from the pre-indication location and ending to this fixed location.
- kind: Definition

###### 3.13.10.4.12 (Requirement Type)
Note: Figure 56 shows the parts of the ceiling speed and braking to target supervision limits, which are used in target speed monitoring to trigger the brake commands and the transitions between supervision statuses. It does not show what is displayed to the driver: in particular, the braking to target Permitted supervision limit is displayed (even if not supervised) for values lower than the release speed.
- WordTraceId: 221909
- atomic: false
- Legal Obligation: not applicable
- implement: false
- implementerEnhanced: Note: Figure 56 shows the parts of the ceiling speed and braking to target supervision limits, which are used in target speed monitoring to trigger the brake commands and the transitions between supervision statuses. It does not show what is displayed to the
  driver
  [EXTERNAL]
  : in particular, the braking to target Permitted supervision limit is displayed (
  even
  if
  [CONDITION]
  [WEAK]
  not supervised) for values lower than the release speed.
- kind: Note
- CrossRefLink -> 3.13.10.4.10[5].[f]56.C

###### 3.13.10.4.12[2] (Requirement Type)
- WordTraceId: 222347
- atomic: false
- Legal Obligation: not applicable
- implement: false
- kind: Placeholder

###### 3.13.10.4.12[2].[t]10 (Requirement Type)
| Revocation condition # | Estimated speed | Train front end position (estimated and max safe) | TI Command revoked | Supervision status revoked |
| --- | --- | --- | --- | --- |
| r0 | [C]0.Position Standstill |  | [C]0.TICommand EB | [C]0.Supervision Intervention status |
| r1 | [C]1.Speed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 | [C]1.Position Not relevant | [C]1.TICommand TCO SB EB (in case V_target ≠ 0, only if allowed by National Value) | [C]1.Supervision Indication status Overspeed status Warning status Intervention status (in case of EB command and V_target ≠ 0, only if allowed by National Value) |
| r2 | [C]2.Speed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 | [C]2.Position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 if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 OR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if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 | [C]2.TICommand TCO SB EB (only if allowed by National Value) | [C]2.Supervision Indication status (only in case of change of displayed target) Overspeed status Warning status Intervention status (in case of EB command and V_target ≠ 0, only if allowed by National Value) |
| r3 | [C]2.Speed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 | [C]3.Position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 if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 OR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 if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 | [C]3.TICommand TCO SB EB (only if allowed by National Value) | [C]3.Supervision Overspeed status Warning status Intervention status (in case of EB command, only if allowed by National Value) |
- WordTraceId: 223410
- atomic: false
- Legal Obligation: not applicable
- implement: false
- kind: Table

###### 3.13.10.4.12[2].[t]10.C (Requirement Type)
Table {Table 10}: Revocation of Train Interface commands and supervision statuses in target speed monitoring, MRSP target or LOA
- WordTraceId: 223410
- atomic: true
- Legal Obligation: unknown
- PlainText: Table 10: Revocation of Train Interface commands and supervision statuses in target speed monitoring, MRSP target or LOA
- implement: false
- kind: Table

###### 3.13.10.4.12[2].[t]10.[C]0 (Requirement Type)
- WordTraceId: 222483
- atomic: false
- Legal Obligation: not applicable
- implement: false
- kind: Table

###### 3.13.10.4.12[2].[t]10.[C]0.Position (Requirement Type)
Standstill
- WordTraceId: 222486
- atomic: true
- Legal Obligation: unknown
- implement: true
- kind: ordinary

###### 3.13.10.4.12[2].[t]10.[C]0.TICommand (Requirement Type)
EB
- WordTraceId: 222497
- atomic: true
- Legal Obligation: unknown
- implement: true
- kind: ordinary

###### 3.13.10.4.12[2].[t]10.[C]0.Supervision (Requirement Type)
Intervention status
- WordTraceId: 222500
- atomic: true
- Legal Obligation: unknown
- implement: true
- kind: ordinary

###### 3.13.10.4.12[2].[t]10.[C]1 (Requirement Type)
- WordTraceId: 222521
- atomic: false
- Legal Obligation: not applicable
- implement: false
- kind: Table

###### 3.13.10.4.12[2].[t]10.[C]1.Speed (Requirement Type)
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- WordTraceId: 222524
- atomic: true
- Legal Obligation: unknown
- implement: true
- kind: ordinary

###### 3.13.10.4.12[2].[t]10.[C]1.Position (Requirement Type)
Not relevant
- WordTraceId: 222548
- atomic: true
- Legal Obligation: unknown
- implement: true
- kind: ordinary

###### 3.13.10.4.12[2].[t]10.[C]1.TICommand (Requirement Type)
CONTENTS HAVE BEEN SPLIT UP - SEE CHILDREN
- WordTraceId: 222561
- atomic: false
- Legal Obligation: not applicable
- implement: false
- kind: ordinary

###### 3.13.10.4.12[2].[t]10.[C]1.TICommand.[1] (Requirement Type)
TCO
- WordTraceId: 222561
- atomic: true
- Legal Obligation: unknown
- implement: true
- kind: ordinary

###### 3.13.10.4.12[2].[t]10.[C]1.TICommand.[2] (Requirement Type)
SB
- WordTraceId: 222565
- atomic: true
- Legal Obligation: unknown
- implement: true
- kind: ordinary

###### 3.13.10.4.12[2].[t]10.[C]1.TICommand.[3] (Requirement Type)
EB (in case V_target ≠ 0, only if allowed by National Value)
- WordTraceId: 222568
- atomic: true
- Legal Obligation: unknown
- implement: true
- implementerEnhanced: EB (
  in case
  [CONDITION]
  V_target ≠ 0, only
  if
  [CONDITION]
  allowed by National Value)
- kind: ordinary

###### 3.13.10.4.12[2].[t]10.[C]1.Supervision (Requirement Type)
CONTENTS HAVE BEEN SPLIT UP - SEE CHILDREN
- WordTraceId: 222629
- atomic: false
- Legal Obligation: not applicable
- implement: false
- kind: ordinary

###### 3.13.10.4.12[2].[t]10.[C]1.Supervision.[1] (Requirement Type)
Indication status
- WordTraceId: 222629
- atomic: true
- Legal Obligation: unknown
- implement: true
- kind: ordinary

###### 3.13.10.4.12[2].[t]10.[C]1.Supervision.[2] (Requirement Type)
Overspeed status
- WordTraceId: 222647
- atomic: true
- Legal Obligation: unknown
- implement: true
- kind: ordinary

###### 3.13.10.4.12[2].[t]10.[C]1.Supervision.[3] (Requirement Type)
Warning status
- WordTraceId: 222664
- atomic: true
- Legal Obligation: unknown
- implement: true
- kind: ordinary

###### 3.13.10.4.12[2].[t]10.[C]1.Supervision.[4] (Requirement Type)
Intervention status (in case of EB command and V_target ≠ 0, only if allowed by National Value)
- WordTraceId: 222679
- atomic: true
- Legal Obligation: unknown
- implement: true
- implementerEnhanced: Intervention status (
  in case of
  [CONDITION]
  EB command and V_target ≠ 0, only
  if
  [CONDITION]
  allowed by National Value)
- kind: ordinary

###### 3.13.10.4.12[2].[t]10.[C]2 (Requirement Type)
- WordTraceId: 222776
- atomic: false
- Legal Obligation: not applicable
- implement: false
- kind: Table

###### 3.13.10.4.12[2].[t]10.[C]2.Speed (Requirement Type)
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- WordTraceId: 222779
- atomic: true
- Legal Obligation: unknown
- implement: true
- kind: ordinary

###### 3.13.10.4.12[2].[t]10.[C]2.Position (Requirement Type)
CONTENTS HAVE BEEN SPLIT UP - SEE CHILDREN
- WordTraceId: 222803
- atomic: false
- Legal Obligation: not applicable
- implement: false
- kind: ordinary

###### 3.13.10.4.12[2].[t]10.[C]2.Position.[1] (Requirement Type)
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if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
- WordTraceId: 222803
- atomic: true
- Legal Obligation: unknown
- PlainText: if
- implement: true
- implementerEnhanced: if
  [CONDITION]
- kind: ordinary

###### 3.13.10.4.12[2].[t]10.[C]2.Position.[2] (Requirement Type)
OR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if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
- WordTraceId: 222853
- atomic: true
- Legal Obligation: unknown
- PlainText: OR if
- implement: true
- implementerEnhanced: OR
  if
  [CONDITION]
- kind: ordinary

###### 3.13.10.4.12[2].[t]10.[C]2.TICommand (Requirement Type)
CONTENTS HAVE BEEN SPLIT UP - SEE CHILDREN
- WordTraceId: 222906
- atomic: false
- Legal Obligation: not applicable
- implement: false
- kind: ordinary

###### 3.13.10.4.12[2].[t]10.[C]2.TICommand.[1] (Requirement Type)
TCO
- WordTraceId: 222906
- atomic: true
- Legal Obligation: unknown
- implement: true
- kind: ordinary

###### 3.13.10.4.12[2].[t]10.[C]2.TICommand.[2] (Requirement Type)
SB
- WordTraceId: 222910
- atomic: true
- Legal Obligation: unknown
- implement: true
- kind: ordinary

###### 3.13.10.4.12[2].[t]10.[C]2.TICommand.[3] (Requirement Type)
EB (only if allowed by National Value)
- WordTraceId: 222913
- atomic: true
- Legal Obligation: unknown
- implement: true
- implementerEnhanced: EB (only
  if
  [CONDITION]
  allowed by National Value)
- kind: ordinary

###### 3.13.10.4.12[2].[t]10.[C]2.Supervision (Requirement Type)
CONTENTS HAVE BEEN SPLIT UP - SEE CHILDREN
- WordTraceId: 222952
- atomic: false
- Legal Obligation: not applicable
- implement: false
- kind: ordinary

###### 3.13.10.4.12[2].[t]10.[C]2.Supervision.[1] (Requirement Type)
Indication status (only in case of change of displayed target)
- WordTraceId: 222952
- atomic: true
- Legal Obligation: unknown
- implement: true
- implementerEnhanced: Indication status (only
  in case of
  [CONDITION]
  change of displayed target)
- kind: ordinary

###### 3.13.10.4.12[2].[t]10.[C]2.Supervision.[2] (Requirement Type)
Overspeed status
- WordTraceId: 223015
- atomic: true
- Legal Obligation: unknown
- implement: true
- kind: ordinary

###### 3.13.10.4.12[2].[t]10.[C]2.Supervision.[3] (Requirement Type)
Warning status
- WordTraceId: 223032
- atomic: true
- Legal Obligation: unknown
- implement: true
- kind: ordinary

###### 3.13.10.4.12[2].[t]10.[C]2.Supervision.[4] (Requirement Type)
Intervention status (in case of EB command and V_target ≠ 0, only if allowed by National Value)
- WordTraceId: 223047
- atomic: true
- Legal Obligation: unknown
- implement: true
- implementerEnhanced: Intervention status (
  in case of
  [CONDITION]
  EB command and V_target ≠ 0, only
  if
  [CONDITION]
  allowed by National Value)
- kind: ordinary

###### 3.13.10.4.12[2].[t]10.[C]3 (Requirement Type)
- WordTraceId: 223144
- atomic: false
- Legal Obligation: not applicable
- implement: false
- kind: Table

###### 3.13.10.4.12[2].[t]10.[C]3.Position (Requirement Type)
CONTENTS HAVE BEEN SPLIT UP - SEE CHILDREN
- WordTraceId: 223148
- atomic: false
- Legal Obligation: not applicable
- implement: false
- kind: ordinary

###### 3.13.10.4.12[2].[t]10.[C]3.Position.[1] (Requirement Type)
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if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
- WordTraceId: 223148
- atomic: true
- Legal Obligation: unknown
- PlainText: if
- implement: true
- implementerEnhanced: if
  [CONDITION]
- kind: ordinary

###### 3.13.10.4.12[2].[t]10.[C]3.Position.[2] (Requirement Type)
OR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 if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
- WordTraceId: 223199
- atomic: true
- Legal Obligation: unknown
- PlainText: OR  if
- implement: true
- implementerEnhanced: OR
  if
  [CONDITION]
- kind: ordinary

###### 3.13.10.4.12[2].[t]10.[C]3.TICommand (Requirement Type)
CONTENTS HAVE BEEN SPLIT UP - SEE CHILDREN
- WordTraceId: 223252
- atomic: false
- Legal Obligation: not applicable
- implement: false
- kind: ordinary

###### 3.13.10.4.12[2].[t]10.[C]3.TICommand.[1] (Requirement Type)
TCO
- WordTraceId: 223252
- atomic: true
- Legal Obligation: unknown
- implement: true
- kind: ordinary

###### 3.13.10.4.12[2].[t]10.[C]3.TICommand.[2] (Requirement Type)
SB
- WordTraceId: 223256
- atomic: true
- Legal Obligation: unknown
- implement: true
- kind: ordinary

###### 3.13.10.4.12[2].[t]10.[C]3.TICommand.[3] (Requirement Type)
EB (only if allowed by National Value)
- WordTraceId: 223259
- atomic: true
- Legal Obligation: unknown
- implement: true
- implementerEnhanced: EB (only
  if
  [CONDITION]
  allowed by National Value)
- kind: ordinary

###### 3.13.10.4.12[2].[t]10.[C]3.Supervision (Requirement Type)
CONTENTS HAVE BEEN SPLIT UP - SEE CHILDREN
- WordTraceId: 223298
- atomic: false
- Legal Obligation: not applicable
- implement: false
- kind: ordinary

###### 3.13.10.4.12[2].[t]10.[C]3.Supervision.[1] (Requirement Type)
Overspeed status
- WordTraceId: 223298
- atomic: true
- Legal Obligation: unknown
- implement: true
- kind: ordinary

###### 3.13.10.4.12[2].[t]10.[C]3.Supervision.[2] (Requirement Type)
Warning status
- WordTraceId: 223315
- atomic: true
- Legal Obligation: unknown
- implement: true
- kind: ordinary

###### 3.13.10.4.12[2].[t]10.[C]3.Supervision.[3] (Requirement Type)
Intervention status (in case of EB command, only if allowed by National Value)
- WordTraceId: 223330
- atomic: true
- Legal Obligation: unknown
- implement: true
- implementerEnhanced: Intervention status (
  in case of
  [CONDITION]
  EB command, only
  if
  [CONDITION]
  allowed by National Value)
- kind: ordinary

###### 3.13.10.4.12[3] (Requirement Type)
- WordTraceId: 223556
- atomic: false
- Legal Obligation: not applicable
- implement: false
- kind: Placeholder

###### 3.13.10.4.12[3].[t]11 (Requirement Type)
| Revocation condition # | Estimated speed | Train front end position (estimated and max safe) | TI Command revoked | Supervision status revoked |
| --- | --- | --- | --- | --- |
| r0 | [C]0.Position Standstill |  | [C]0.TICommand EB | [C]0.Supervision Intervention status |
| r1 | [C]1.Speed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 | [C]1.Position Not relevant | [C]1.TICommand TCO SB EB (in case V_target ≠ 0, only if allowed by National Value) | [C]1.Supervision Indication status (only in case of change of displayed target) Overspeed status Warning status Intervention status (in case of EB command and V_target ≠ 0, only if allowed by National Value) |
| r2 | [C]2.Speed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 | [C]2.Position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 if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 OR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if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 | [C]2.TICommand TCO SB EB (only if allowed by National Value) | [C]2.Supervision Indication status (only in case of change of displayed target) Overspeed status Warning status Intervention status (in case of EB command and V_target ≠ 0, only if allowed by National Value) |
| r3 | [C]2.Speed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 | [C]3.Position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 if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 OR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 if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 | [C]3.TICommand TCO SB EB (only if allowed by National Value) | [C]3.Supervision Overspeed status Warning status Intervention status (in case of EB command, only if allowed by National Value) |
- WordTraceId: 224664
- atomic: false
- Legal Obligation: not applicable
- implement: false
- kind: Table

###### 3.13.10.4.12[3].[t]11.C (Requirement Type)
Table {Table 11}: Revocation of Train Interface commands and supervision statuses in target speed monitoring, EOA/SvL with release speed
- WordTraceId: 224664
- atomic: true
- Legal Obligation: unknown
- PlainText: Table 11: Revocation of Train Interface commands and supervision statuses in target speed monitoring, EOA/SvL with release speed
- implement: false
- kind: Table

###### 3.13.10.4.12[3].[t]11.[C]0 (Requirement Type)
- WordTraceId: 223692
- atomic: false
- Legal Obligation: not applicable
- implement: false
- kind: Table

###### 3.13.10.4.12[3].[t]11.[C]0.Position (Requirement Type)
Standstill
- WordTraceId: 223695
- atomic: true
- Legal Obligation: unknown
- implement: true
- kind: ordinary

###### 3.13.10.4.12[3].[t]11.[C]0.TICommand (Requirement Type)
EB
- WordTraceId: 223706
- atomic: true
- Legal Obligation: unknown
- implement: true
- kind: ordinary

###### 3.13.10.4.12[3].[t]11.[C]0.Supervision (Requirement Type)
Intervention status
- WordTraceId: 223709
- atomic: true
- Legal Obligation: unknown
- implement: true
- kind: ordinary

###### 3.13.10.4.12[3].[t]11.[C]1 (Requirement Type)
- WordTraceId: 223730
- atomic: false
- Legal Obligation: not applicable
- implement: false
- kind: Table

###### 3.13.10.4.12[3].[t]11.[C]1.Speed (Requirement Type)
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- WordTraceId: 223733
- atomic: true
- Legal Obligation: unknown
- implement: true
- kind: ordinary

###### 3.13.10.4.12[3].[t]11.[C]1.Position (Requirement Type)
Not relevant
- WordTraceId: 223757
- atomic: true
- Legal Obligation: unknown
- implement: true
- kind: ordinary

###### 3.13.10.4.12[3].[t]11.[C]1.TICommand (Requirement Type)
CONTENTS HAVE BEEN SPLIT UP - SEE CHILDREN
- WordTraceId: 223770
- atomic: false
- Legal Obligation: not applicable
- implement: false
- kind: ordinary

###### 3.13.10.4.12[3].[t]11.[C]1.TICommand.[1] (Requirement Type)
TCO
- WordTraceId: 223770
- atomic: true
- Legal Obligation: unknown
- implement: true
- kind: ordinary

###### 3.13.10.4.12[3].[t]11.[C]1.TICommand.[2] (Requirement Type)
SB
- WordTraceId: 223774
- atomic: true
- Legal Obligation: unknown
- implement: true
- kind: ordinary

###### 3.13.10.4.12[3].[t]11.[C]1.TICommand.[3] (Requirement Type)
EB (in case V_target ≠ 0, only if allowed by National Value)
- WordTraceId: 223777
- atomic: true
- Legal Obligation: unknown
- implement: true
- implementerEnhanced: EB (
  in case
  [CONDITION]
  V_target ≠ 0, only
  if
  [CONDITION]
  allowed by National Value)
- kind: ordinary

###### 3.13.10.4.12[3].[t]11.[C]1.Supervision (Requirement Type)
CONTENTS HAVE BEEN SPLIT UP - SEE CHILDREN
- WordTraceId: 223838
- atomic: false
- Legal Obligation: not applicable
- implement: false
- kind: ordinary

###### 3.13.10.4.12[3].[t]11.[C]1.Supervision.[1] (Requirement Type)
Indication status (only in case of change of displayed target)
- WordTraceId: 223838
- atomic: true
- Legal Obligation: unknown
- implement: true
- implementerEnhanced: Indication status (only
  in case of
  [CONDITION]
  change of displayed target)
- kind: ordinary

###### 3.13.10.4.12[3].[t]11.[C]1.Supervision.[2] (Requirement Type)
Overspeed status
- WordTraceId: 223901
- atomic: true
- Legal Obligation: unknown
- implement: true
- kind: ordinary

###### 3.13.10.4.12[3].[t]11.[C]1.Supervision.[3] (Requirement Type)
Warning status
- WordTraceId: 223918
- atomic: true
- Legal Obligation: unknown
- implement: true
- kind: ordinary

###### 3.13.10.4.12[3].[t]11.[C]1.Supervision.[4] (Requirement Type)
Intervention status (in case of EB command and V_target ≠ 0, only if allowed by National Value)
- WordTraceId: 223933
- atomic: true
- Legal Obligation: unknown
- implement: true
- implementerEnhanced: Intervention status (
  in case of
  [CONDITION]
  EB command and V_target ≠ 0, only
  if
  [CONDITION]
  allowed by National Value)
- kind: ordinary

###### 3.13.10.4.12[3].[t]11.[C]2 (Requirement Type)
- WordTraceId: 224030
- atomic: false
- Legal Obligation: not applicable
- implement: false
- kind: Table

###### 3.13.10.4.12[3].[t]11.[C]2.Speed (Requirement Type)
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- WordTraceId: 224033
- atomic: true
- Legal Obligation: unknown
- implement: true
- kind: ordinary

###### 3.13.10.4.12[3].[t]11.[C]2.Position (Requirement Type)
CONTENTS HAVE BEEN SPLIT UP - SEE CHILDREN
- WordTraceId: 224057
- atomic: false
- Legal Obligation: not applicable
- implement: false
- kind: ordinary

###### 3.13.10.4.12[3].[t]11.[C]2.Position.[1] (Requirement Type)
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if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
- WordTraceId: 224057
- atomic: true
- Legal Obligation: unknown
- PlainText: if
- implement: true
- implementerEnhanced: if
  [CONDITION]
- kind: ordinary

###### 3.13.10.4.12[3].[t]11.[C]2.Position.[2] (Requirement Type)
OR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if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
- WordTraceId: 224107
- atomic: true
- Legal Obligation: unknown
- PlainText: OR if
- implement: true
- implementerEnhanced: OR
  if
  [CONDITION]
- kind: ordinary

###### 3.13.10.4.12[3].[t]11.[C]2.TICommand (Requirement Type)
CONTENTS HAVE BEEN SPLIT UP - SEE CHILDREN
- WordTraceId: 224160
- atomic: false
- Legal Obligation: not applicable
- implement: false
- kind: ordinary

###### 3.13.10.4.12[3].[t]11.[C]2.TICommand.[1] (Requirement Type)
TCO
- WordTraceId: 224160
- atomic: true
- Legal Obligation: unknown
- implement: true
- kind: ordinary

###### 3.13.10.4.12[3].[t]11.[C]2.TICommand.[2] (Requirement Type)
SB
- WordTraceId: 224164
- atomic: true
- Legal Obligation: unknown
- implement: true
- kind: ordinary

###### 3.13.10.4.12[3].[t]11.[C]2.TICommand.[3] (Requirement Type)
EB (only if allowed by National Value)
- WordTraceId: 224167
- atomic: true
- Legal Obligation: unknown
- implement: true
- implementerEnhanced: EB (only
  if
  [CONDITION]
  allowed by National Value)
- kind: ordinary

###### 3.13.10.4.12[3].[t]11.[C]2.Supervision (Requirement Type)
CONTENTS HAVE BEEN SPLIT UP - SEE CHILDREN
- WordTraceId: 224206
- atomic: false
- Legal Obligation: not applicable
- implement: false
- kind: ordinary

###### 3.13.10.4.12[3].[t]11.[C]2.Supervision.[1] (Requirement Type)
Indication status (only in case of change of displayed target)
- WordTraceId: 224206
- atomic: true
- Legal Obligation: unknown
- implement: true
- implementerEnhanced: Indication status (only
  in case of
  [CONDITION]
  change of displayed target)
- kind: ordinary

###### 3.13.10.4.12[3].[t]11.[C]2.Supervision.[2] (Requirement Type)
Overspeed status
- WordTraceId: 224269
- atomic: true
- Legal Obligation: unknown
- implement: true
- kind: ordinary

###### 3.13.10.4.12[3].[t]11.[C]2.Supervision.[3] (Requirement Type)
Warning status
- WordTraceId: 224286
- atomic: true
- Legal Obligation: unknown
- implement: true
- kind: ordinary

###### 3.13.10.4.12[3].[t]11.[C]2.Supervision.[4] (Requirement Type)
Intervention status (in case of EB command and V_target ≠ 0, only if allowed by National Value)
- WordTraceId: 224301
- atomic: true
- Legal Obligation: unknown
- implement: true
- implementerEnhanced: Intervention status (
  in case of
  [CONDITION]
  EB command and V_target ≠ 0, only
  if
  [CONDITION]
  allowed by National Value)
- kind: ordinary

###### 3.13.10.4.12[3].[t]11.[C]3 (Requirement Type)
- WordTraceId: 224398
- atomic: false
- Legal Obligation: not applicable
- implement: false
- kind: Table

###### 3.13.10.4.12[3].[t]11.[C]3.Position (Requirement Type)
CONTENTS HAVE BEEN SPLIT UP - SEE CHILDREN
- WordTraceId: 224402
- atomic: false
- Legal Obligation: not applicable
- implement: false
- kind: ordinary

###### 3.13.10.4.12[3].[t]11.[C]3.Position.[1] (Requirement Type)
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if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
- WordTraceId: 224402
- atomic: true
- Legal Obligation: unknown
- PlainText: if
- implement: true
- implementerEnhanced: if
  [CONDITION]
- kind: ordinary

###### 3.13.10.4.12[3].[t]11.[C]3.Position.[2] (Requirement Type)
OR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 if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
- WordTraceId: 224453
- atomic: true
- Legal Obligation: unknown
- PlainText: OR  if
- implement: true
- implementerEnhanced: OR
  if
  [CONDITION]
- kind: ordinary

###### 3.13.10.4.12[3].[t]11.[C]3.TICommand (Requirement Type)
CONTENTS HAVE BEEN SPLIT UP - SEE CHILDREN
- WordTraceId: 224506
- atomic: false
- Legal Obligation: not applicable
- implement: false
- kind: ordinary

###### 3.13.10.4.12[3].[t]11.[C]3.TICommand.[1] (Requirement Type)
TCO
- WordTraceId: 224506
- atomic: true
- Legal Obligation: unknown
- implement: true
- kind: ordinary

###### 3.13.10.4.12[3].[t]11.[C]3.TICommand.[2] (Requirement Type)
SB
- WordTraceId: 224510
- atomic: true
- Legal Obligation: unknown
- implement: true
- kind: ordinary

###### 3.13.10.4.12[3].[t]11.[C]3.TICommand.[3] (Requirement Type)
EB (only if allowed by National Value)
- WordTraceId: 224513
- atomic: true
- Legal Obligation: unknown
- implement: true
- implementerEnhanced: EB (only
  if
  [CONDITION]
  allowed by National Value)
- kind: ordinary

###### 3.13.10.4.12[3].[t]11.[C]3.Supervision (Requirement Type)
CONTENTS HAVE BEEN SPLIT UP - SEE CHILDREN
- WordTraceId: 224552
- atomic: false
- Legal Obligation: not applicable
- implement: false
- kind: ordinary

###### 3.13.10.4.12[3].[t]11.[C]3.Supervision.[1] (Requirement Type)
Overspeed status
- WordTraceId: 224552
- atomic: true
- Legal Obligation: unknown
- implement: true
- kind: ordinary

###### 3.13.10.4.12[3].[t]11.[C]3.Supervision.[2] (Requirement Type)
Warning status
- WordTraceId: 224569
- atomic: true
- Legal Obligation: unknown
- implement: true
- kind: ordinary

###### 3.13.10.4.12[3].[t]11.[C]3.Supervision.[3] (Requirement Type)
Intervention status (in case of EB command, only if allowed by National Value)
- WordTraceId: 224584
- atomic: true
- Legal Obligation: unknown
- implement: true
- implementerEnhanced: Intervention status (
  in case of
  [CONDITION]
  EB command, only
  if
  [CONDITION]
  allowed by National Value)
- kind: ordinary

###### 3.13.10.4.13 (Requirement Type)
In case of target EOA/SvL without any supervised release speed, the Table 9 and Table 11 shall be applied, by substituting V_release with the value 0.
- WordTraceId: 224817
- atomic: true
- Legal Obligation: mandatory
- implement: true
- implementerEnhanced: In case of
  [CONDITION]
  target EOA/SvL without any supervised release speed, the Table 9 and Table 11 shall be applied, by substituting V_release with the value 0.
- kind: ordinary
- CrossRefLink -> 3.13.10.4.10[4].[t]9.C
- CrossRefLink -> 3.13.10.4.12[3].[t]11.C

###### 3.13.10.4.14 (Requirement Type)
Note: as long as the same MRSP or LOA target is displayed, the on-board will revoke the Indication status only when the estimated speed does no longer exceed the target speed. On the other hand, as long as the same EOA/SvL target is displayed, the Indication status, once it is triggered, is never revoked. However, for all types of target and only in case of MRDT change, the on-board will revoke the Indication status if the Indication supervision limit (speed and location) is not exceeded (see Table 10 and Table 11).
- WordTraceId: 225020
- atomic: false
- Legal Obligation: not applicable
- implement: false
- implementerEnhanced: Note:
  as long as
  [TIME]
  the same MRSP or LOA target is displayed, the on-board will revoke the Indication status only
  when
  [CONDITION]
  the estimated speed does no longer exceed the target speed. On the other hand,
  as long as
  [TIME]
  the same EOA/SvL target is displayed, the Indication status, once it is triggered, is never revoked. However,
  for all
  [LOOP]
  types of target and only
  in case of
  [CONDITION]
  MRDT change, the on-board will revoke the Indication status
  if
  [CONDITION]
  the Indication supervision limit (speed and location) is not exceeded (see Table 10 and Table 11).
- kind: Note
- CrossRefLink -> 3.13.10.4.12[2].[t]10.C
- CrossRefLink -> 3.13.10.4.12[3].[t]11.C

###### 3.13.10.4.15 (Requirement Type)
The on-board equipment shall execute the transitions between the different supervision statuses as described in Table 12 (see section 4.6.1 for details about the symbols). This table takes into account the order of precedence between the supervision statuses and the possible changes of the displayed target (MRDT), e.g. when the list of supervised targets is updated.
- WordTraceId: 225594
- atomic: false
- Legal Obligation: mandatory
- implement: true
- implementerEnhanced: The
  on-board equipment
  [SELF]
  shall execute the transitions between the different supervision statuses as described in Table 12 (see section 4.6.1 for details about the symbols). This table takes into account the order of precedence between the supervision statuses and the possible changes of the displayed target (MRDT),
  e.g.
  [WEAK]
  when
  [CONDITION]
  the list of supervised targets is updated.
- kind: ordinary
- CrossRefLink -> 3.13.10.4.15[2].[t]12.C
- CrossRefLink -> 4.6.1

###### 3.13.10.4.15[2] (Requirement Type)
- WordTraceId: 225989
- atomic: false
- Legal Obligation: not applicable
- implement: false
- kind: Placeholder

###### 3.13.10.4.15[2].[t]12 (Requirement Type)
| Normal status | [r][1].Indicationstatus_Normalstatus < r1, r2 -p1- | [r][1].Overspeedstatus_Normalstatus < r1, r2 -p1- | [r][1].Warningstatus_Normalstatus < r1, r2 -p1- | [r][1].Interventionstatus_Normalstatus < r0, r1, r2 -p1- |
| --- | --- | --- | --- | --- |
| [r][2].Normalstatus_Indicationstatus t3 > -p4- | Indication status | [r][2].Overspeedstatus_Indicationstatus < r3 -p2- | [r][2].Warningstatus_Indicationstatus < r3 -p2- | [r][2].Interventionstatus_Indicationstatus < r3 -p2- |
| [r][3].Normalstatus_Overspeedstatus t4, t5, t6 > -p3- | [r][3].Indicationstatus_Overspeedstatus t4, t5, t6 > -p3- | Overspeed status |  |  |
| [r][4].Normalstatus_Warningstatus t7, t8, t9 > -p2- | [r][4].Indicationstatus_Warningstatus t7, t8, t9 > -p2- | [r][4].Overspeedstatus_Warningstatus t7, t8, t9 > -p2- | Warning status |  |
| [r][5].Normalstatus_Interventionstatus t10, t11, t12, t13, t14 > -p1- | [r][5].Indicationstatus_Interventionstatus t10, t11, t12, t13, t14 > -p1- | [r][5].Overspeedstatus_Interventionstatus t10, t11, t12, t13, t14 > -p1- | [r][5].Warningstatus_Interventionstatus t10, t11, t12, t13, t14 > -p1- | Intervention status |
- WordTraceId: 226395
- atomic: false
- Legal Obligation: not applicable
- implement: false
- kind: Table

###### 3.13.10.4.15[2].[t]12.C (Requirement Type)
Table {Table 12}: Transitions between supervision statuses in target speed monitoring
- WordTraceId: 226395
- atomic: true
- Legal Obligation: unknown
- PlainText: Table 12: Transitions between supervision statuses in target speed monitoring
- implement: false
- kind: Table

###### 3.13.10.4.15[2].[t]12.[r][1] (Requirement Type)
- WordTraceId: 225989
- atomic: false
- Legal Obligation: not applicable
- implement: false
- kind: Table

###### 3.13.10.4.15[2].[t]12.[r][1].Indicationstatus_Normalstatus (Requirement Type)
< r1, r2
-p1-
- WordTraceId: 226003
- atomic: true
- Legal Obligation: unknown
- PlainText: < r1, r2 -p1-
- implement: true
- kind: ordinary

###### 3.13.10.4.15[2].[t]12.[r][1].Overspeedstatus_Normalstatus (Requirement Type)
< r1, r2
-p1-
- WordTraceId: 226017
- atomic: true
- Legal Obligation: unknown
- PlainText: < r1, r2 -p1-
- implement: true
- kind: ordinary

###### 3.13.10.4.15[2].[t]12.[r][1].Warningstatus_Normalstatus (Requirement Type)
< r1, r2
-p1-
- WordTraceId: 226031
- atomic: true
- Legal Obligation: unknown
- PlainText: < r1, r2 -p1-
- implement: true
- kind: ordinary

###### 3.13.10.4.15[2].[t]12.[r][1].Interventionstatus_Normalstatus (Requirement Type)
< r0, r1, r2
-p1-
- WordTraceId: 226045
- atomic: true
- Legal Obligation: unknown
- PlainText: < r0, r1, r2 -p1-
- implement: true
- kind: ordinary

###### 3.13.10.4.15[2].[t]12.[r][2] (Requirement Type)
- WordTraceId: 226064
- atomic: false
- Legal Obligation: not applicable
- implement: false
- kind: Table

###### 3.13.10.4.15[2].[t]12.[r][2].Normalstatus_Indicationstatus (Requirement Type)
t3 >
-p4-
- WordTraceId: 226064
- atomic: true
- Legal Obligation: unknown
- PlainText: t3 > -p4-
- implement: true
- kind: ordinary

###### 3.13.10.4.15[2].[t]12.[r][2].Overspeedstatus_Indicationstatus (Requirement Type)
< r3
-p2-
- WordTraceId: 226092
- atomic: true
- Legal Obligation: unknown
- PlainText: < r3 -p2-
- implement: true
- kind: ordinary

###### 3.13.10.4.15[2].[t]12.[r][2].Warningstatus_Indicationstatus (Requirement Type)
< r3
-p2-
- WordTraceId: 226102
- atomic: true
- Legal Obligation: unknown
- PlainText: < r3 -p2-
- implement: true
- kind: ordinary

###### 3.13.10.4.15[2].[t]12.[r][2].Interventionstatus_Indicationstatus (Requirement Type)
< r3
-p2-
- WordTraceId: 226112
- atomic: true
- Legal Obligation: unknown
- PlainText: < r3 -p2-
- implement: true
- kind: ordinary

###### 3.13.10.4.15[2].[t]12.[r][3] (Requirement Type)
- WordTraceId: 226123
- atomic: false
- Legal Obligation: not applicable
- implement: false
- kind: Table

###### 3.13.10.4.15[2].[t]12.[r][3].Normalstatus_Overspeedstatus (Requirement Type)
t4, t5, t6 >
-p3-
- WordTraceId: 226123
- atomic: true
- Legal Obligation: unknown
- PlainText: t4, t5, t6 > -p3-
- implement: true
- kind: ordinary

###### 3.13.10.4.15[2].[t]12.[r][3].Indicationstatus_Overspeedstatus (Requirement Type)
t4, t5, t6 >
-p3-
- WordTraceId: 226141
- atomic: true
- Legal Obligation: unknown
- PlainText: t4, t5, t6 > -p3-
- implement: true
- kind: ordinary

###### 3.13.10.4.15[2].[t]12.[r][4] (Requirement Type)
- WordTraceId: 226179
- atomic: false
- Legal Obligation: not applicable
- implement: false
- kind: Table

###### 3.13.10.4.15[2].[t]12.[r][4].Normalstatus_Warningstatus (Requirement Type)
t7, t8, t9 >
-p2-
- WordTraceId: 226179
- atomic: true
- Legal Obligation: unknown
- PlainText: t7, t8, t9 > -p2-
- implement: true
- kind: ordinary

###### 3.13.10.4.15[2].[t]12.[r][4].Indicationstatus_Warningstatus (Requirement Type)
t7, t8, t9 >
-p2-
- WordTraceId: 226197
- atomic: true
- Legal Obligation: unknown
- PlainText: t7, t8, t9 > -p2-
- implement: true
- kind: ordinary

###### 3.13.10.4.15[2].[t]12.[r][4].Overspeedstatus_Warningstatus (Requirement Type)
t7, t8, t9 >
-p2-
- WordTraceId: 226215
- atomic: true
- Legal Obligation: unknown
- PlainText: t7, t8, t9 > -p2-
- implement: true
- kind: ordinary

###### 3.13.10.4.15[2].[t]12.[r][5] (Requirement Type)
- WordTraceId: 226250
- atomic: false
- Legal Obligation: not applicable
- implement: false
- kind: Table

###### 3.13.10.4.15[2].[t]12.[r][5].Normalstatus_Interventionstatus (Requirement Type)
t10, t11, t12, t13, t14 >
-p1-
- WordTraceId: 226250
- atomic: true
- Legal Obligation: unknown
- PlainText: t10, t11, t12, t13, t14 > -p1-
- implement: true
- kind: ordinary

###### 3.13.10.4.15[2].[t]12.[r][5].Indicationstatus_Interventionstatus (Requirement Type)
t10, t11, t12, t13, t14 >
-p1-
- WordTraceId: 226281
- atomic: true
- Legal Obligation: unknown
- PlainText: t10, t11, t12, t13, t14 > -p1-
- implement: true
- kind: ordinary

###### 3.13.10.4.15[2].[t]12.[r][5].Overspeedstatus_Interventionstatus (Requirement Type)
t10, t11, t12, t13, t14 >
-p1-
- WordTraceId: 226312
- atomic: true
- Legal Obligation: unknown
- PlainText: t10, t11, t12, t13, t14 > -p1-
- implement: true
- kind: ordinary

###### 3.13.10.4.15[2].[t]12.[r][5].Warningstatus_Interventionstatus (Requirement Type)
t10, t11, t12, t13, t14 >
-p1-
- WordTraceId: 226343
- atomic: true
- Legal Obligation: unknown
- PlainText: t10, t11, t12, t13, t14 > -p1-
- implement: true
- kind: ordinary

###### 3.13.10.4.16 (Requirement Type)
When the speed and distance monitoring function becomes active and the target speed monitoring is the first one entered, the triggering conditions t1 and t2 defined in Table 8 or Table 9 shall be checked in order to determine whether the Normal status applies. If it is not the case, the on-board shall immediately set the supervision status to the relevant value, applying a transition from the Normal status according to Table 12.
- WordTraceId: 226497
- atomic: false
- Legal Obligation: mandatory
- implement: true
- implementerEnhanced: When
  [CONDITION]
  the speed and distance monitoring function becomes active and the target speed monitoring is the first one entered, the triggering conditions t1 and t2 defined in Table 8 or Table 9 shall be checked in order to determine
  whether
  [CONDITION]
  the Normal status applies.
  If
  [CONDITION]
  it is not the case, the on-board shall
  immediately
  [WEAK]
  set the supervision status to the relevant value, applying a transition from the Normal status according to Table 12.
- kind: ordinary
- CrossRefLink -> 3.13.10.4.10[2].[t]8.C
- CrossRefLink -> 3.13.10.4.10[4].[t]9.C
- CrossRefLink -> 3.13.10.4.15[2].[t]12.C

##### 3.13.10.5 (Requirement Type)
Requirements for release speed monitoring
- WordTraceId: 227008
- atomic: false
- Legal Obligation: not applicable
- implement: false
- kind: Heading

###### 3.13.10.5.1 (Requirement Type)
The on-board equipment shall display the Release speed.
- WordTraceId: 227050
- atomic: true
- Legal Obligation: mandatory
- implement: true
- implementerEnhanced: The
  on-board equipment
  [SELF]
  shall display the Release speed.
- kind: ordinary

###### 3.13.10.5.2 (Requirement Type)
The on-board equipment shall display the target distance, in the same way as for target speed monitoring.
- WordTraceId: 227106
- atomic: true
- Legal Obligation: mandatory
- implement: true
- implementerEnhanced: The
  on-board equipment
  [SELF]
  shall display the target distance, in the same way as for target speed monitoring.
- kind: ordinary

###### 3.13.10.5.3 (Requirement Type)
The braking to target Permitted speed supervision limit related to the MRDT (i.e. EOA or SvL), as calculated in target speed monitoring from the EBD or SBD, shall also be displayed.
- WordTraceId: 227212
- atomic: false
- Legal Obligation: mandatory
- implement: true
- kind: ordinary

###### 3.13.10.5.4 (Requirement Type)
The on-board equipment shall compare the estimated speed with the release speed and shall trigger/revoke commands to the train interface (emergency brake) and supervision statuses as described in Table 13 and Table 14.
- WordTraceId: 227394
- atomic: false
- Legal Obligation: mandatory
- implement: true
- implementerEnhanced: The
  on-board equipment
  [SELF]
  shall compare the estimated speed with the release speed and shall trigger/revoke commands to the train interface (emergency brake) and supervision statuses as described in Table 13 and Table 14.
- kind: ordinary
- CrossRefLink -> 3.13.10.5.4[2].[t]13.C
- CrossRefLink -> 3.13.10.5.4[3].[t]14.C

###### 3.13.10.5.4[2] (Requirement Type)
- WordTraceId: 227665
- atomic: false
- Legal Obligation: not applicable
- implement: false
- kind: Placeholder

###### 3.13.10.5.4[2].[t]13 (Requirement Type)
| Triggeringcondition # | Estimated speed | Location | TI Command triggered | Supervision status triggered |
| --- | --- | --- | --- | --- |
| t1 | [C]1.Speed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 | [C]1.Position Any | [C]1.TICommand - | [C]1.Supervision Indication Status |
| t2 | [C]2.Speed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 | [C]2.Position Any | [C]2.TICommand EB | [C]2.Supervision Intervention Status |
- WordTraceId: 227871
- atomic: false
- Legal Obligation: not applicable
- implement: false
- kind: Table

###### 3.13.10.5.4[2].[t]13.C (Requirement Type)
Table {Table 13}: Triggering of Train Interface commands and supervision statuses
in release speed monitoring
- WordTraceId: 227871
- atomic: true
- Legal Obligation: unknown
- PlainText: Table 13: Triggering of Train Interface commands and supervision statuses in release speed monitoring
- implement: false
- kind: Table

###### 3.13.10.5.4[2].[t]13.[C]1 (Requirement Type)
- WordTraceId: 227764
- atomic: false
- Legal Obligation: not applicable
- implement: false
- kind: Table

###### 3.13.10.5.4[2].[t]13.[C]1.Speed (Requirement Type)
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- WordTraceId: 227767
- atomic: true
- Legal Obligation: unknown
- implement: true
- kind: ordinary

###### 3.13.10.5.4[2].[t]13.[C]1.Position (Requirement Type)
Any
- WordTraceId: 227791
- atomic: true
- Legal Obligation: unknown
- implement: true
- kind: ordinary

###### 3.13.10.5.4[2].[t]13.[C]1.TICommand (Requirement Type)
-
- WordTraceId: 227795
- atomic: true
- Legal Obligation: unknown
- implement: true
- kind: ordinary

###### 3.13.10.5.4[2].[t]13.[C]1.Supervision (Requirement Type)
Indication Status
- WordTraceId: 227797
- atomic: true
- Legal Obligation: unknown
- implement: true
- kind: ordinary

###### 3.13.10.5.4[2].[t]13.[C]2 (Requirement Type)
- WordTraceId: 227816
- atomic: false
- Legal Obligation: not applicable
- implement: false
- kind: Table

###### 3.13.10.5.4[2].[t]13.[C]2.Speed (Requirement Type)
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- WordTraceId: 227819
- atomic: true
- Legal Obligation: unknown
- implement: true
- kind: ordinary

###### 3.13.10.5.4[2].[t]13.[C]2.Position (Requirement Type)
Any
- WordTraceId: 227843
- atomic: true
- Legal Obligation: unknown
- implement: true
- kind: ordinary

###### 3.13.10.5.4[2].[t]13.[C]2.TICommand (Requirement Type)
EB
- WordTraceId: 227847
- atomic: true
- Legal Obligation: unknown
- implement: true
- kind: ordinary

###### 3.13.10.5.4[2].[t]13.[C]2.Supervision (Requirement Type)
Intervention Status
- WordTraceId: 227850
- atomic: true
- Legal Obligation: unknown
- implement: true
- kind: ordinary

###### 3.13.10.5.4[3] (Requirement Type)
- WordTraceId: 227997
- atomic: false
- Legal Obligation: not applicable
- implement: false
- kind: Placeholder

###### 3.13.10.5.4[3].[t]14 (Requirement Type)
| Triggeringcondition # | Estimated speed | Location | TI Command revoked | Supervision status revoked |
| --- | --- | --- | --- | --- |
| r0 | [C]0.Position Standstill |  | [C]0.TICommand EB | [C]0.Supervision Intervention Status |
| r1 | [C]1.Speed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 | [C]1.Position Any | [C]1.TICommand - | [C]1.Supervision Overspeed Status Warning Status |
- WordTraceId: 228196
- atomic: false
- Legal Obligation: not applicable
- implement: false
- kind: Table

###### 3.13.10.5.4[3].[t]14.C (Requirement Type)
Table {Table 14}: Revocation of Train Interface commands and supervision statuses
in release speed monitoring
- WordTraceId: 228196
- atomic: true
- Legal Obligation: unknown
- PlainText: Table 14: Revocation of Train Interface commands and supervision statuses in release speed monitoring
- implement: false
- kind: Table

###### 3.13.10.5.4[3].[t]14.[C]0 (Requirement Type)
- WordTraceId: 228092
- atomic: false
- Legal Obligation: not applicable
- implement: false
- kind: Table

###### 3.13.10.5.4[3].[t]14.[C]0.Position (Requirement Type)
Standstill
- WordTraceId: 228095
- atomic: true
- Legal Obligation: unknown
- implement: true
- kind: ordinary

###### 3.13.10.5.4[3].[t]14.[C]0.TICommand (Requirement Type)
EB
- WordTraceId: 228106
- atomic: true
- Legal Obligation: unknown
- implement: true
- kind: ordinary

###### 3.13.10.5.4[3].[t]14.[C]0.Supervision (Requirement Type)
Intervention Status
- WordTraceId: 228109
- atomic: true
- Legal Obligation: unknown
- implement: true
- kind: ordinary

###### 3.13.10.5.4[3].[t]14.[C]1 (Requirement Type)
- WordTraceId: 228130
- atomic: false
- Legal Obligation: not applicable
- implement: false
- kind: Table

###### 3.13.10.5.4[3].[t]14.[C]1.Speed (Requirement Type)
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- WordTraceId: 228133
- atomic: true
- Legal Obligation: unknown
- implement: true
- kind: ordinary

###### 3.13.10.5.4[3].[t]14.[C]1.Position (Requirement Type)
Any
- WordTraceId: 228157
- atomic: true
- Legal Obligation: unknown
- implement: true
- kind: ordinary

###### 3.13.10.5.4[3].[t]14.[C]1.TICommand (Requirement Type)
-
- WordTraceId: 228161
- atomic: true
- Legal Obligation: unknown
- implement: true
- kind: ordinary

###### 3.13.10.5.4[3].[t]14.[C]1.Supervision (Requirement Type)
CONTENTS HAVE BEEN SPLIT UP - SEE CHILDREN
- WordTraceId: 228163
- atomic: false
- Legal Obligation: not applicable
- implement: false
- kind: ordinary

###### 3.13.10.5.4[3].[t]14.[C]1.Supervision.[1] (Requirement Type)
Overspeed Status
- WordTraceId: 228163
- atomic: true
- Legal Obligation: unknown
- implement: true
- kind: ordinary

###### 3.13.10.5.4[3].[t]14.[C]1.Supervision.[2] (Requirement Type)
Warning Status
- WordTraceId: 228180
- atomic: true
- Legal Obligation: unknown
- implement: true
- kind: ordinary

###### 3.13.10.5.5 (Requirement Type)
The on-board equipment shall execute the transitions between the different supervision statuses as described in Table 15 (see section 4.6.1 for details about the symbols). This table takes into account the order of precedence between the supervision statuses and the possible updates of the release speed while in release speed monitoring.
- WordTraceId: 228322
- atomic: false
- Legal Obligation: mandatory
- implement: true
- implementerEnhanced: The
  on-board equipment
  [SELF]
  shall execute the transitions between the different supervision statuses as described in Table 15 (see section 4.6.1 for details about the symbols). This table takes into account the order of precedence between the supervision statuses and the possible updates of the release speed
  while
  [TIME]
  in release speed monitoring.
- kind: ordinary
- CrossRefLink -> 3.13.10.5.5[2].[t]15.C
- CrossRefLink -> 4.6.1

###### 3.13.10.5.5[2] (Requirement Type)
- WordTraceId: 228688
- atomic: false
- Legal Obligation: not applicable
- implement: false
- kind: Placeholder

###### 3.13.10.5.5[2].[t]15 (Requirement Type)
| Normal status |  |  |  |  |
| --- | --- | --- | --- | --- |
| [r][2].Normalstatus_Indicationstatus t1 > -p1- | Indication status | [r][2].Overspeedstatus_Indicationstatus < r1 -p1- | [r][2].Warningstatus_Indicationstatus < r1 -p1- | [r][2].Interventionstatus_Indicationstatus < r0 -p1- |
|  |  | Overspeed status |  |  |
|  |  |  | Warning status |  |
| [r][5].Normalstatus_Interventionstatus t2 > -p1- | [r][5].Indicationstatus_Interventionstatus t2 > -p1- | [r][5].Overspeedstatus_Interventionstatus t2 > -p1- | [r][5].Warningstatus_Interventionstatus t2 > -p1- | Intervention status |
- WordTraceId: 228869
- atomic: false
- Legal Obligation: not applicable
- implement: false
- kind: Table

###### 3.13.10.5.5[2].[t]15.C (Requirement Type)
Table {Table 15}: Transitions between supervision statuses in release speed monitoring
- WordTraceId: 228869
- atomic: true
- Legal Obligation: unknown
- PlainText: Table 15: Transitions between supervision statuses in release speed monitoring
- implement: false
- kind: Table

###### 3.13.10.5.5[2].[t]15.[r][2] (Requirement Type)
- WordTraceId: 228707
- atomic: false
- Legal Obligation: not applicable
- implement: false
- kind: Table

###### 3.13.10.5.5[2].[t]15.[r][2].Normalstatus_Indicationstatus (Requirement Type)
t1 >
-p1-
- WordTraceId: 228707
- atomic: true
- Legal Obligation: unknown
- PlainText: t1 > -p1-
- implement: true
- kind: ordinary

###### 3.13.10.5.5[2].[t]15.[r][2].Overspeedstatus_Indicationstatus (Requirement Type)
< r1
-p1-
- WordTraceId: 228735
- atomic: true
- Legal Obligation: unknown
- PlainText: < r1 -p1-
- implement: true
- kind: ordinary

###### 3.13.10.5.5[2].[t]15.[r][2].Warningstatus_Indicationstatus (Requirement Type)
< r1
-p1-
- WordTraceId: 228745
- atomic: true
- Legal Obligation: unknown
- PlainText: < r1 -p1-
- implement: true
- kind: ordinary

###### 3.13.10.5.5[2].[t]15.[r][2].Interventionstatus_Indicationstatus (Requirement Type)
< r0
-p1-
- WordTraceId: 228755
- atomic: true
- Legal Obligation: unknown
- PlainText: < r0 -p1-
- implement: true
- kind: ordinary

###### 3.13.10.5.5[2].[t]15.[r][5] (Requirement Type)
- WordTraceId: 228808
- atomic: false
- Legal Obligation: not applicable
- implement: false
- kind: Table

###### 3.13.10.5.5[2].[t]15.[r][5].Normalstatus_Interventionstatus (Requirement Type)
t2 >
-p1-
- WordTraceId: 228808
- atomic: true
- Legal Obligation: unknown
- PlainText: t2 > -p1-
- implement: true
- kind: ordinary

###### 3.13.10.5.5[2].[t]15.[r][5].Indicationstatus_Interventionstatus (Requirement Type)
t2 >
-p1-
- WordTraceId: 228818
- atomic: true
- Legal Obligation: unknown
- PlainText: t2 > -p1-
- implement: true
- kind: ordinary

###### 3.13.10.5.5[2].[t]15.[r][5].Overspeedstatus_Interventionstatus (Requirement Type)
t2 >
-p1-
- WordTraceId: 228828
- atomic: true
- Legal Obligation: unknown
- PlainText: t2 > -p1-
- implement: true
- kind: ordinary

###### 3.13.10.5.5[2].[t]15.[r][5].Warningstatus_Interventionstatus (Requirement Type)
t2 >
-p1-
- WordTraceId: 228838
- atomic: true
- Legal Obligation: unknown
- PlainText: t2 > -p1-
- implement: true
- kind: ordinary

###### 3.13.10.5.6 (Requirement Type)
When the speed and distance monitoring function becomes active and the release speed monitoring is the first one entered, the triggering condition t1 defined in Table 13 shall be checked in order to determine whether the Indication status applies. If it is not the case, the on-board shall immediately set the supervision status to the Intervention status, applying a transition from the Indication status according to Table 15.
- WordTraceId: 228972
- atomic: false
- Legal Obligation: mandatory
- implement: true
- implementerEnhanced: When
  [CONDITION]
  the speed and distance monitoring function becomes active and the release speed monitoring is the first one entered, the triggering condition t1 defined in Table 13 shall be checked in order to determine
  whether
  [CONDITION]
  the Indication status applies.
  If
  [CONDITION]
  it is not the case, the on-board shall
  immediately
  [WEAK]
  set the supervision status to the Intervention status, applying a transition from the Indication status according to Table 15.
- kind: ordinary
- CrossRefLink -> 3.13.10.5.4[2].[t]13.C
- CrossRefLink -> 3.13.10.5.5[2].[t]15.C

###### 3.13.10.5.7 (Requirement Type)
The Normal, Warning and Overspeed statuses are not used in release speed monitoring. However, in case the release speed monitoring is entered and the supervision status was previously set to Normal, Warning or Overspeed, the on-board equipment shall immediately execute one of the transitions from respectively the Normal, Warning or Overspeed status, as described in Table 15.
- WordTraceId: 229453
- atomic: false
- Legal Obligation: mandatory
- implement: true
- implementerEnhanced: The Normal, Warning and Overspeed statuses are not used in release speed monitoring. However,
  in case
  [CONDITION]
  the release speed monitoring is entered and the supervision status was previously set to Normal, Warning or Overspeed, the
  on-board equipment
  [SELF]
  shall
  immediately
  [WEAK]
  execute one of the transitions from respectively the Normal, Warning or Overspeed status, as described in Table 15.
- kind: ordinary
- CrossRefLink -> 3.13.10.5.5[2].[t]15.C

##### 3.13.10.6 (Requirement Type)
Transitions between types of Speed and distance monitoring
- WordTraceId: 229857
- atomic: false
- Legal Obligation: not applicable
- implement: false
- kind: Heading

###### 3.13.10.6.1 (Requirement Type)
The transitions between the Ceiling speed monitoring, the Target speed monitoring and the Release speed monitoring shall be achieved as described in the Table 16:
- WordTraceId: 229916
- atomic: true
- Legal Obligation: mandatory
- implement: true
- kind: ordinary
- CrossRefLink -> 3.13.10.6.1[2].[t]16.C

###### 3.13.10.6.1[2] (Requirement Type)
- WordTraceId: 230105
- atomic: false
- Legal Obligation: not applicable
- implement: false
- kind: Placeholder

###### 3.13.10.6.1[2].[t]16 (Requirement Type)
| Condition id | Transition condition | CSM | TSM | RSM |
| --- | --- | --- | --- | --- |
| [1] | [C]1.Content (The train has passed with its max safe front end the pre-indication location calculated from an EBD) OR (The train has passed with its estimated front end the pre-indication location calculated from the SBD) | [C]1.CSM ARROW TO: [C]1.TSM | [C]1.TSM |  |
| [2] | [C]2.Content (The train has passed with its max safe front end the RSM start location if it is calculated from an EBD) OR (The train has passed with its estimated front end the RSM start location if it is calculated from the SBD) |  | [C]2.TSM ARROW TO: [C]2.RSM | [C]2.RSM |
| [3] | [C]3.Content (The list of supervised targets is updated) AND (condition [1] is not fulfilled) | [C]3.CSM | [C]3.TSM ARROW TO: [C]3.CSM | [C]3.RSM ARROW TO: [C]3.CSM |
| [4] | [C]4.Content (The list of supervised targets is updated) AND (condition [1] is fulfilled) AND (condition [2] is not fulfilled) | [C]4.CSM ARROW TO: [C]4.TSM | [C]4.TSM | [C]4.RSM ARROW TO: [C]4.TSM |
| [5] | [C]5.Content (The list of supervised targets is updated) AND (condition [2] is fulfilled) | [C]5.CSM ARROW TO: [C]5.RSM | [C]5.TSM ARROW TO: [C]5.RSM | [C]5.RSM |
- WordTraceId: 230908
- atomic: false
- Legal Obligation: not applicable
- implement: false
- kind: Table

###### 3.13.10.6.1[2].[t]16.C (Requirement Type)
Table {Table 16}: Transitions between types of Speed and distance monitoring
- WordTraceId: 230908
- atomic: true
- Legal Obligation: unknown
- PlainText: Table 16: Transitions between types of Speed and distance monitoring
- implement: false
- kind: Table

###### 3.13.10.6.1[2].[t]16.[C]1 (Requirement Type)
- WordTraceId: 230152
- atomic: false
- Legal Obligation: not applicable
- implement: false
- kind: Table

###### 3.13.10.6.1[2].[t]16.[C]1.Content (Requirement Type)
(The train has passed with its max safe front end the pre-indication location calculated from an EBD) OR (The train has passed with its estimated front end the pre-indication location calculated from the SBD)
- WordTraceId: 230156
- atomic: true
- Legal Obligation: unknown
- implement: true
- kind: ordinary

###### 3.13.10.6.1[2].[t]16.[C]1.CSM (Requirement Type)
ARROW TO: [C]1.TSM
- WordTraceId: 230365
- atomic: true
- Legal Obligation: unknown
- implement: true
- kind: ordinary

###### 3.13.10.6.1[2].[t]16.[C]1.TSM (Requirement Type)
- WordTraceId: 230368
- atomic: true
- Legal Obligation: unknown
- implement: true
- kind: ordinary

###### 3.13.10.6.1[2].[t]16.[C]2 (Requirement Type)
- WordTraceId: 230371
- atomic: false
- Legal Obligation: not applicable
- implement: false
- kind: Table

###### 3.13.10.6.1[2].[t]16.[C]2.Content (Requirement Type)
(The train has passed with its max safe front end the RSM start location if it is calculated from an EBD) OR (The train has passed with its estimated front end the RSM start location if it is calculated from the SBD)
- WordTraceId: 230375
- atomic: true
- Legal Obligation: unknown
- implement: true
- implementerEnhanced: (The train has passed with its max safe front end the RSM start location
  if
  [CONDITION]
  it is calculated from an EBD) OR (The train has passed with its estimated front end the RSM start location
  if
  [CONDITION]
  it is calculated from the SBD)
- kind: ordinary

###### 3.13.10.6.1[2].[t]16.[C]2.TSM (Requirement Type)
ARROW TO: [C]2.RSM
- WordTraceId: 230593
- atomic: true
- Legal Obligation: unknown
- implement: true
- kind: ordinary

###### 3.13.10.6.1[2].[t]16.[C]2.RSM (Requirement Type)
- WordTraceId: 230596
- atomic: true
- Legal Obligation: unknown
- implement: true
- kind: ordinary

###### 3.13.10.6.1[2].[t]16.[C]3 (Requirement Type)
- WordTraceId: 230598
- atomic: false
- Legal Obligation: not applicable
- implement: false
- kind: Table

###### 3.13.10.6.1[2].[t]16.[C]3.Content (Requirement Type)
(The list of supervised targets is updated) AND (condition [1] is not fulfilled)
- WordTraceId: 230602
- atomic: true
- Legal Obligation: unknown
- implement: true
- kind: ordinary

###### 3.13.10.6.1[2].[t]16.[C]3.CSM (Requirement Type)
- WordTraceId: 230683
- atomic: true
- Legal Obligation: unknown
- implement: true
- kind: ordinary

###### 3.13.10.6.1[2].[t]16.[C]3.TSM (Requirement Type)
ARROW TO: [C]3.CSM
- WordTraceId: 230686
- atomic: true
- Legal Obligation: unknown
- implement: true
- kind: ordinary

###### 3.13.10.6.1[2].[t]16.[C]3.RSM (Requirement Type)
ARROW TO: [C]3.CSM
- WordTraceId: 230688
- atomic: true
- Legal Obligation: unknown
- implement: true
- kind: ordinary

###### 3.13.10.6.1[2].[t]16.[C]4 (Requirement Type)
- WordTraceId: 230692
- atomic: false
- Legal Obligation: not applicable
- implement: false
- kind: Table

###### 3.13.10.6.1[2].[t]16.[C]4.Content (Requirement Type)
(The list of supervised targets is updated) AND (condition [1] is fulfilled) AND (condition [2] is not fulfilled)
- WordTraceId: 230696
- atomic: true
- Legal Obligation: unknown
- implement: true
- kind: ordinary

###### 3.13.10.6.1[2].[t]16.[C]4.CSM (Requirement Type)
ARROW TO: [C]4.TSM
- WordTraceId: 230810
- atomic: true
- Legal Obligation: unknown
- implement: true
- kind: ordinary

###### 3.13.10.6.1[2].[t]16.[C]4.TSM (Requirement Type)
- WordTraceId: 230813
- atomic: true
- Legal Obligation: unknown
- implement: true
- kind: ordinary

###### 3.13.10.6.1[2].[t]16.[C]4.RSM (Requirement Type)
ARROW TO: [C]4.TSM
- WordTraceId: 230815
- atomic: true
- Legal Obligation: unknown
- implement: true
- kind: ordinary

###### 3.13.10.6.1[2].[t]16.[C]5 (Requirement Type)
- WordTraceId: 230818
- atomic: false
- Legal Obligation: not applicable
- implement: false
- kind: Table

###### 3.13.10.6.1[2].[t]16.[C]5.Content (Requirement Type)
(The list of supervised targets is updated) AND (condition [2] is fulfilled)
- WordTraceId: 230822
- atomic: true
- Legal Obligation: unknown
- implement: true
- kind: ordinary

###### 3.13.10.6.1[2].[t]16.[C]5.CSM (Requirement Type)
ARROW TO: [C]5.RSM
- WordTraceId: 230899
- atomic: true
- Legal Obligation: unknown
- implement: true
- kind: ordinary

###### 3.13.10.6.1[2].[t]16.[C]5.TSM (Requirement Type)
ARROW TO: [C]5.RSM
- WordTraceId: 230902
- atomic: true
- Legal Obligation: unknown
- implement: true
- kind: ordinary

###### 3.13.10.6.1[2].[t]16.[C]5.RSM (Requirement Type)
- WordTraceId: 230906
- atomic: true
- Legal Obligation: unknown
- implement: true
- kind: ordinary

###### 3.13.10.6.2 (Requirement Type)
If a transition of speed and distance monitoring occurs while a brake command is already applied, the concerned command shall be maintained until the revocation condition, if specified for the newly entered speed and distance monitoring, is fulfilled.
- WordTraceId: 231001
- atomic: true
- Legal Obligation: mandatory
- implement: true
- implementerEnhanced: If
  [CONDITION]
  a transition of speed and distance monitoring occurs
  while
  [TIME]
  a brake command is already applied, the concerned command shall be maintained
  until
  [TIME]
  the revocation condition,
  if
  [CONDITION]
  specified for the newly entered speed and distance monitoring, is fulfilled.
- kind: ordinary

###### 3.13.10.6.2.1 (Requirement Type)
Note: This means that when the service brake is commanded in ceiling speed monitoring while it is not available in target speed monitoring, the service brake remains commanded when the on-board switches to target speed monitoring and is only revoked when the Permitted speed supervision limit is no longer exceeded.
- WordTraceId: 231253
- atomic: false
- Legal Obligation: not applicable
- implement: false
- implementerEnhanced: Note: This means that
  when
  [CONDITION]
  the service brake is commanded in ceiling speed monitoring
  while
  [TIME]
  it is not available in target speed monitoring, the service brake remains commanded
  when
  [CONDITION]
  the on-board switches to target speed monitoring and is only revoked
  when
  [CONDITION]
  the Permitted speed supervision limit is no longer exceeded.
- kind: Note

###### 3.13.10.6.3 (Requirement Type)
If a transition from target speed monitoring to ceiling speed or release speed monitoring occurs while a traction cut-off command is already applied, the traction cut-off command shall be immediately revoked.
- WordTraceId: 231569
- atomic: true
- Legal Obligation: mandatory
- implement: true
- implementerEnhanced: If
  [CONDITION]
  a transition from target speed monitoring to ceiling speed or release speed monitoring occurs
  while
  [TIME]
  a traction cut-off command is already applied, the traction cut-off command shall be
  immediately
  [WEAK]
  revoked.
- kind: ordinary

###### 3.13.10.6.4 (Requirement Type)
If a transition from target speed monitoring to release speed monitoring occurs while a service brake command is already applied, the service brake command shall be immediately revoked.
- WordTraceId: 231778
- atomic: true
- Legal Obligation: mandatory
- implement: true
- implementerEnhanced: If
  [CONDITION]
  a transition from target speed monitoring to release speed monitoring occurs
  while
  [TIME]
  a service brake command is already applied, the service brake command shall be
  immediately
  [WEAK]
  revoked.
- kind: ordinary

###### 3.13.10.6.5 (Requirement Type)
On executing a transition between types of speed and distance monitoring, the supervision status shall be determined according to the requirements specified for the newly entered speed and distance monitoring.
- WordTraceId: 231964
- atomic: true
- Legal Obligation: mandatory
- implement: true
- kind: ordinary

### 3.14 (Requirement Type)
Brake Command Handling and Protection against Undesirable Train Movement
- WordTraceId: 232174
- atomic: false
- Legal Obligation: not applicable
- implement: false
- kind: Heading

#### 3.14.1 (Requirement Type)
Brake Command Handling
- WordTraceId: 232247
- atomic: false
- Legal Obligation: not applicable
- implement: false
- kind: Heading

##### 3.14.1.1 (Requirement Type)
Note: Whenever the type of brake used is not specified explicitly in the text, it shall be interpreted as not being important for technical interoperability and being a property of the specific implementation.
- WordTraceId: 232270
- atomic: false
- Legal Obligation: mandatory
- implement: false
- kind: Note

##### 3.14.1.2 (Requirement Type)
In case only the application of (the non-vital) service brake has been commanded and the service brake fails to be applied, the emergency brake command shall be given.
- WordTraceId: 232482
- atomic: true
- Legal Obligation: mandatory
- implement: true
- implementerEnhanced: In case
  [CONDITION]
  only the application of (the non-vital) service brake has been commanded and the service brake fails to be applied, the emergency brake command shall be given.
- kind: ordinary

##### 3.14.1.3 (Requirement Type)
If the emergency brake command was triggered due to a trip condition (see chapter 4) the emergency brake command shall be released at standstill and after driver acknowledgement of the trip condition.
- WordTraceId: 232651
- atomic: true
- Legal Obligation: mandatory
- implement: true
- implementerEnhanced: If
  [CONDITION]
  the emergency brake command was triggered due to a trip condition (see chapter 4) the emergency brake command shall be released at standstill and
  after
  [TIME]
  driver
  [EXTERNAL]
  acknowledgement of the trip condition.
- kind: ordinary

##### 3.14.1.4 (Requirement Type)
For handling of brake commands resulting from the speed and distance monitoring, refer to section 3.13.10.
- WordTraceId: 232852
- atomic: true
- Legal Obligation: unknown
- implement: true
- kind: ordinary
- CrossRefLink -> 3.13.10

##### 3.14.1.5 (Requirement Type)
If the brake command was triggered due to roll away protection, reverse movement protection or standstill supervision the brake command shall be released at standstill and after driver acknowledgement.
- WordTraceId: 232959
- atomic: true
- Legal Obligation: mandatory
- implement: true
- implementerEnhanced: If
  [CONDITION]
  the brake command was triggered due to roll away protection, reverse movement protection or standstill supervision the brake command shall be released at standstill and
  after
  [TIME]
  driver
  [EXTERNAL]
  acknowledgement.
- kind: ordinary

##### 3.14.1.6 (Requirement Type)
If the brake command was triggered due to linking error, balise group message inconsistency or RAMS related supervision error, the brake command shall be released at standstill.
- WordTraceId: 233162
- atomic: true
- Legal Obligation: mandatory
- implement: true
- implementerEnhanced: If
  [CONDITION]
  the brake command was triggered due to linking error,
  balise group
  [EXTERNAL]
  message inconsistency or RAMS related supervision error, the brake command shall be released at standstill.
- kind: ordinary

##### 3.14.1.7 (Requirement Type)
If the brake command was triggered due to supervision of the safe radio connection (T_NVCONTACT) the brake command shall be released at standstill or if a new consistent message has been received from the RBC.
- WordTraceId: 233340
- atomic: true
- Legal Obligation: mandatory
- implement: true
- implementerEnhanced: If
  [CONDITION]
  the brake command was triggered due to supervision of the safe radio connection (T_NVCONTACT) the brake command shall be released at standstill or
  if
  [CONDITION]
  a new consistent message has been received from the
  RBC
  [EXTERNAL]
  .
- kind: ordinary

###### 3.14.1.7.1 (Requirement Type)
If the brake command was triggered due to an overpassed reversing distance related to a reversing area or due to any further movement in the direction opposite to the train orientation while the reversing distance is still overpassed, the brake command shall be released if the reversing distance becomes extended so that the reversing distance is no longer overpassed, or at standstill after driver acknowledgement.
- WordTraceId: 233551
- atomic: true
- Legal Obligation: mandatory
- implement: true
- implementerEnhanced: If
  [CONDITION]
  the brake command was triggered due to an overpassed reversing distance related to a reversing area or due to any further movement in the direction opposite to the train orientation
  while
  [TIME]
  the reversing distance is still overpassed, the brake command shall be released
  if
  [CONDITION]
  the reversing distance becomes extended so that the reversing distance is no longer overpassed, or at standstill
  after
  [TIME]
  driver
  [EXTERNAL]
  acknowledgement.
- kind: ordinary

###### 3.14.1.7.2 (Requirement Type)
If the brake command was triggered due to change of Train Data while running (see section 5.17 procedure "Changing Train Data from sources different from the driver”), the brake command shall be released at standstill and after driver acknowledgement.
- WordTraceId: 233968
- atomic: true
- Legal Obligation: mandatory
- implement: true
- implementerEnhanced: If
  [CONDITION]
  the brake command was triggered due to change of Train Data
  while
  [TIME]
  running (see section 5.17 procedure "Changing Train Data from sources different from the
  driver
  [EXTERNAL]
  ”), the brake command shall be released at standstill and
  after
  [TIME]
  driver
  [EXTERNAL]
  acknowledgement.
- kind: ordinary
- CrossRefLink -> 5.17

###### 3.14.1.7.3 (Requirement Type)
If the brake command was triggered due to the detection of a train movement while modifying/revalidating train data or while entering SR speed/distance limits, the brake command shall be released at standstill and after driver acknowledgement..
- WordTraceId: 234220
- atomic: true
- Legal Obligation: mandatory
- implement: true
- implementerEnhanced: If
  [CONDITION]
  the brake command was triggered due to the detection of a train movement
  while
  [TIME]
  modifying/revalidating train data or
  while
  [TIME]
  entering SR speed/distance limits, the brake command shall be released at standstill and
  after
  [TIME]
  driver
  [EXTERNAL]
  acknowledgement..
- kind: ordinary

###### 3.14.1.7.4 (Requirement Type)
If the brake command was triggered due to an overpassed distance allowed for moving backwards in Post Trip mode or due to any further movement in the direction opposite to the train orientation while the distance allowed for moving backwards in Post Trip mode is still overpassed, the brake command shall be released at standstill and after driver acknowledgement.
- WordTraceId: 234465
- atomic: true
- Legal Obligation: mandatory
- implement: true
- implementerEnhanced: If
  [CONDITION]
  the brake command was triggered due to an overpassed distance allowed for moving backwards in Post Trip mode or due to any further movement in the direction opposite to the train orientation
  while
  [TIME]
  the distance allowed for moving backwards in Post Trip mode is still overpassed, the brake command shall be released at standstill and
  after
  [TIME]
  driver
  [EXTERNAL]
  acknowledgement.
- kind: ordinary

###### 3.14.1.7.5 (Requirement Type)
If the brake command was triggered due to the driver not having acknowledged a text message, the brake command shall be released after the driver has acknowledged the text message.
- WordTraceId: 234830
- atomic: true
- Legal Obligation: mandatory
- implement: true
- implementerEnhanced: If
  [CONDITION]
  the brake command was triggered due to the
  driver
  [EXTERNAL]
  not having acknowledged a text message, the brake command shall be released
  after
  [TIME]
  the
  driver
  [EXTERNAL]
  has acknowledged the text message.
- kind: ordinary

##### 3.14.1.8 (Requirement Type)
An indication shall be given to the driver to indicate when the brakes can be released and when an acknowledgement is requested.
- WordTraceId: 235011
- atomic: true
- Legal Obligation: mandatory
- implement: true
- implementerEnhanced: An indication shall be given to the
  driver
  [EXTERNAL]
  to indicate
  when
  [CONDITION]
  the brakes can be released and
  when
  [CONDITION]
  an acknowledgement is requested.
- kind: ordinary

#### 3.14.2 (Requirement Type)
Roll Away Protection
- WordTraceId: 235140
- atomic: false
- Legal Obligation: not applicable
- implement: false
- kind: Heading

##### 3.14.2.1 (Requirement Type)
Note: This protection is only applicable if the required information can be obtained from the direction controller.
- WordTraceId: 235161
- atomic: false
- Legal Obligation: not applicable
- implement: false
- implementerEnhanced: Note: This protection is only applicable
  if
  [CONDITION]
  the required information can be obtained from the direction controller.
- kind: Note

##### 3.14.2.2 (Requirement Type)
The Roll Away Protection (RAP) shall prevent the train from moving in a direction, which conflicts with the current position of the direction controller in the active desk.
- WordTraceId: 235277
- atomic: true
- Legal Obligation: mandatory
- implement: true
- kind: ordinary

##### 3.14.2.3 (Requirement Type)
If the controller is in neutral position, the RAP shall prevent forward and reverse movements of the train.
- WordTraceId: 235450
- atomic: true
- Legal Obligation: mandatory
- implement: true
- implementerEnhanced: If
  [CONDITION]
  the controller is in neutral position, the RAP shall prevent forward and reverse movements of the train.
- kind: ordinary

##### 3.14.2.4 (Requirement Type)
When the system recognises a movement exceeding the national value for the allowed roll away distance the brakes shall be triggered.
- WordTraceId: 235558
- atomic: true
- Legal Obligation: mandatory
- implement: true
- implementerEnhanced: When
  [CONDITION]
  the system recognises a movement exceeding the national value for the allowed roll away distance the brakes shall be triggered.
- kind: ordinary

##### 3.14.2.5 (Requirement Type)
Refer to section 3.14.1.
- WordTraceId: 235691
- atomic: true
- Legal Obligation: unknown
- implement: true
- kind: ordinary
- CrossRefLink -> 3.14.1

##### 3.14.2.6 (Requirement Type)
An indication shall be given to the driver showing when the RAP is commanding the brakes.
- WordTraceId: 235745
- atomic: true
- Legal Obligation: mandatory
- implement: true
- implementerEnhanced: An indication shall be given to the
  driver
  [EXTERNAL]
  showing
  when
  [CONDITION]
  the RAP is commanding the brakes.
- kind: ordinary

##### 3.14.2.7 (Requirement Type)
After revocation of the brake command the RAP will be re-initialised using the current position of the train as the new reference location.
- WordTraceId: 235835
- atomic: true
- Legal Obligation: unknown
- implement: true
- implementerEnhanced: After
  [TIME]
  revocation of the brake command the RAP will be
  re-initialised
  [AGAIN]
  using the current position of the train as the new reference location.
- kind: ordinary

#### 3.14.3 (Requirement Type)
Reverse Movement Protection
- WordTraceId: 235975
- atomic: false
- Legal Obligation: not applicable
- implement: false
- kind: Heading

##### 3.14.3.1 (Requirement Type)
The Reverse Movement Protection (RMP) shall prevent the train from moving in the opposite direction to the permitted one. The permitted movement direction of a train shall be the one of the currently valid MA, if available on-board. See chapter 4 concerning permitted direction for special cases.
- WordTraceId: 236003
- atomic: false
- Legal Obligation: mandatory
- implement: true
- implementerEnhanced: The Reverse Movement Protection (RMP) shall prevent the train from moving in the opposite direction to the permitted one. The permitted movement direction of a train shall be the one of the currently valid MA,
  if
  [CONDITION]
  available on-board. See chapter 4 concerning permitted direction for special cases.
- kind: ordinary

##### 3.14.3.2 (Requirement Type)
When a reverse movement is detected, the brake command shall be triggered after a distance specified by the national value.
- WordTraceId: 236300
- atomic: true
- Legal Obligation: mandatory
- implement: true
- implementerEnhanced: When
  [CONDITION]
  a reverse movement is detected, the brake command shall be triggered
  after
  [TIME]
  a distance specified by the national value.
- kind: ordinary

##### 3.14.3.3 (Requirement Type)
Refer to section 3.14.1.
- WordTraceId: 236424
- atomic: true
- Legal Obligation: unknown
- implement: true
- kind: ordinary
- CrossRefLink -> 3.14.1

##### 3.14.3.4 (Requirement Type)
An indication shall be given to the driver showing when the RMP is commanding the brakes.
- WordTraceId: 236478
- atomic: true
- Legal Obligation: mandatory
- implement: true
- implementerEnhanced: An indication shall be given to the
  driver
  [EXTERNAL]
  showing
  when
  [CONDITION]
  the RMP is commanding the brakes.
- kind: ordinary

##### 3.14.3.5 (Requirement Type)
After revocation of the brake command the RMP will be reinitialised using the current position of the train as the new reference location.
- WordTraceId: 236568
- atomic: true
- Legal Obligation: unknown
- implement: true
- implementerEnhanced: After
  [TIME]
  revocation of the brake command the RMP will be reinitialised using the current position of the train as the new reference location.
- kind: ordinary

##### 3.14.3.6 (Requirement Type)
Information received from balises during reverse movement shall be rejected.
- WordTraceId: 236707
- atomic: true
- Legal Obligation: mandatory
- implement: true
- implementerEnhanced: Information received from
  balises
  [EXTERNAL]
  during
  [TIME]
  reverse movement shall be rejected.
- kind: ordinary

#### 3.14.4 (Requirement Type)
Standstill supervision
- WordTraceId: 236784
- atomic: false
- Legal Obligation: not applicable
- implement: false
- kind: Heading

##### 3.14.4.1 (Requirement Type)
This function shall prevent the train from moving.
- WordTraceId: 236807
- atomic: true
- Legal Obligation: mandatory
- implement: true
- kind: ordinary

##### 3.14.4.2 (Requirement Type)
When a movement is detected, the brake command shall be triggered after a distance specified by the national value.
- WordTraceId: 236858
- atomic: true
- Legal Obligation: mandatory
- implement: true
- implementerEnhanced: When
  [CONDITION]
  a movement is detected, the brake command shall be triggered
  after
  [TIME]
  a distance specified by the national value.
- kind: ordinary

##### 3.14.4.3 (Requirement Type)
Refer to section 3.14.1.
- WordTraceId: 236974
- atomic: true
- Legal Obligation: unknown
- implement: true
- kind: ordinary
- CrossRefLink -> 3.14.1

##### 3.14.4.4 (Requirement Type)
After revocation of the brake command the standstill supervision will be re-initialised.
- WordTraceId: 237028
- atomic: true
- Legal Obligation: unknown
- implement: true
- implementerEnhanced: After
  [TIME]
  revocation of the brake command the standstill supervision will be
  re-initialised
  [AGAIN]
  .
- kind: ordinary

##### 3.14.4.5 (Requirement Type)
If a cab is active, an indication shall be given to the driver showing when the Standstill Supervision is commanding the brakes.
- WordTraceId: 237118
- atomic: true
- Legal Obligation: mandatory
- implement: true
- implementerEnhanced: If
  [CONDITION]
  a cab is active, an indication shall be given to the
  driver
  [EXTERNAL]
  showing
  when
  [CONDITION]
  the Standstill Supervision is commanding the brakes.
- kind: ordinary

### 3.15 (Requirement Type)
Special functions
- WordTraceId: 237247
- atomic: false
- Legal Obligation: not applicable
- implement: false
- kind: Heading

#### 3.15.1 (Requirement Type)
RBC/RBC Handover
- WordTraceId: 237265
- atomic: false
- Legal Obligation: not applicable
- implement: false
- implementerEnhanced: RBC
  [EXTERNAL]
  /
  RBC
  [EXTERNAL]
  Handover
- kind: Heading

##### 3.15.1.1 (Requirement Type)
Introduction
- WordTraceId: 237282
- atomic: false
- Legal Obligation: not applicable
- implement: false
- kind: Heading

###### 3.15.1.1.1 (Requirement Type)
Trains with one or more radio(s) shall be able to pass from one RBC area to another automatically (without driver action).
- WordTraceId: 237295
- atomic: true
- Legal Obligation: mandatory
- implement: true
- implementerEnhanced: Trains with one or more radio(s) shall be able to pass from one
  RBC
  [EXTERNAL]
  area to another automatically (without
  driver
  [EXTERNAL]
  action).
- kind: ordinary

###### 3.15.1.1.2 (Requirement Type)
Since an RBC is unable to know whether the on-board is able to manage one or two communication session(s) at once, the following principles are applicable for both cases. Thereby, the RBCs will have the same behaviour in both cases.
- WordTraceId: 237418
- atomic: false
- Legal Obligation: unknown
- implement: true
- implementerEnhanced: Since an
  RBC
  [EXTERNAL]
  is unable to know
  whether
  [CONDITION]
  the on-board is able to manage one or two communication session(s) at once, the following principles are applicable for both cases. Thereby, the RBCs will have the same behaviour in both cases.
- kind: ordinary

###### 3.15.1.1.3 (Requirement Type)
An RBC/RBC handover performed by a train with one communication session available may result in performance penalties since it will not be able to “prepare” (session establishment, version determination, …) the expected supervision by the Accepting RBC until the on-board disconnects from the Handing Over RBC.
- WordTraceId: 237651
- atomic: true
- Legal Obligation: optional
- implement: true
- implementerEnhanced: An
  RBC
  [EXTERNAL]
  /
  RBC
  [EXTERNAL]
  handover performed by a train with one communication session available may result in performance penalties since it will not be able to “prepare” (session establishment, version determination, …) the expected supervision by the Accepting
  RBC
  [EXTERNAL]
  until
  [TIME]
  the on-board disconnects from the Handing Over
  RBC
  [EXTERNAL]
  .
- kind: ordinary

###### 3.15.1.1.4 (Requirement Type)
In level 3, trains following the one with one communication session available will always suffer performance penalties since no more position reports will be issued from the disconnection from the Handing Over RBC until the connection to the Accepting RBC.
- WordTraceId: 237962
- atomic: true
- Legal Obligation: unknown
- implement: true
- implementerEnhanced: In level 3, trains following the one with one communication session available will always suffer performance penalties since no more position reports will be issued from the disconnection from the Handing Over
  RBC
  [EXTERNAL]
  until
  [TIME]
  the connection to the Accepting
  RBC
  [EXTERNAL]
  .
- kind: ordinary

##### 3.15.1.2 (Requirement Type)
Handing Over RBC
- WordTraceId: 238219
- atomic: false
- Legal Obligation: not applicable
- implement: false
- implementerEnhanced: Handing Over
  RBC
  [EXTERNAL]
- kind: Heading

###### 3.15.1.2.1 (Requirement Type)
When the Handing Over RBC detects that a route is set for a train to enter another RBC area, it shall send:
- WordTraceId: 238236
- atomic: true
- Legal Obligation: mandatory
- implement: true
- implementerEnhanced: When
  [CONDITION]
  the Handing Over
  RBC
  [EXTERNAL]
  detects that a route is set for a train to enter another
  RBC
  [EXTERNAL]
  area, it shall send:
- kind: ordinary

###### 3.15.1.2.1.a (Requirement Type)
Intentionally deleted.
- WordTraceId: 238344
- atomic: false
- Legal Obligation: not applicable
- implement: false
- ListNumberText: a)
- kind: Placeholder

###### 3.15.1.2.1.b (Requirement Type)
To the Accepting RBC the following information:
- WordTraceId: 238367
- atomic: true
- Legal Obligation: unknown
- implement: false
- implementerEnhanced: To the Accepting
  RBC
  [EXTERNAL]
  the following information:
- ListNumberText: b)
- kind: Heading

###### 3.15.1.2.1.b.*[1] (Requirement Type)
The ETCS identity of the on-board equipment;
- WordTraceId: 238415
- atomic: true
- Legal Obligation: unknown
- implement: true
- implementerEnhanced: The ETCS identity of the
  on-board equipment
  [SELF]
  ;
- ListNumberText: ·
- kind: ordinary

###### 3.15.1.2.1.b.*[2] (Requirement Type)
The border location that will be passed by the train when entering the Accepting RBC area;
- WordTraceId: 238460
- atomic: true
- Legal Obligation: unknown
- implement: true
- implementerEnhanced: The border location that will be passed by the train
  when
  [CONDITION]
  entering the Accepting
  RBC
  [EXTERNAL]
  area;
- ListNumberText: ·
- kind: ordinary

###### 3.15.1.2.1.b.*[3] (Requirement Type)
Current mode of the on-board equipment;
- WordTraceId: 238551
- atomic: true
- Legal Obligation: unknown
- implement: true
- implementerEnhanced: Current mode of the
  on-board equipment
  [SELF]
  ;
- ListNumberText: ·
- kind: ordinary

###### 3.15.1.2.1.b.*[4] (Requirement Type)
Optionally, Train Data;
- WordTraceId: 238591
- atomic: true
- Legal Obligation: unknown
- implement: true
- ListNumberText: ·
- kind: ordinary

###### 3.15.1.2.1.b.*[5] (Requirement Type)
Optionally, for a non-leading engine, the ETCS identity of the leading engine.
- WordTraceId: 238615
- atomic: true
- Legal Obligation: unknown
- implement: true
- ListNumberText: ·
- kind: ordinary

###### 3.15.1.2.2 (Requirement Type)
The Handing Over RBC shall not send information to an on-board equipment concerning the route in advance of the border without receiving the corresponding information from the Accepting RBC.
- WordTraceId: 238694
- atomic: true
- Legal Obligation: mandatory
- implement: true
- implementerEnhanced: The Handing Over
  RBC
  [EXTERNAL]
  shall not send information to an
  on-board equipment
  [SELF]
  concerning the route in advance of the border without receiving the corresponding information from the Accepting
  RBC
  [EXTERNAL]
  .
- kind: ordinary

###### 3.15.1.2.3 (Requirement Type)
It shall be possible for the Handing Over RBC to request route related information from the Accepting RBC, limited to a maximum amount of data.
- WordTraceId: 238885
- atomic: true
- Legal Obligation: mandatory
- implement: true
- implementerEnhanced: It shall be possible for the Handing Over
  RBC
  [EXTERNAL]
  to request route related information from the Accepting
  RBC
  [EXTERNAL]
  , limited to a maximum amount of data.
- kind: ordinary

###### 3.15.1.2.3.1 (Requirement Type)
Note: Route related information is :
- WordTraceId: 239029
- atomic: false
- Legal Obligation: not applicable
- implement: false
- kind: Note

###### 3.15.1.2.3.1.a (Requirement Type)
Movement authorities
- WordTraceId: 239066
- atomic: true
- Legal Obligation: unknown
- implement: false
- ListNumberText: a)
- kind: Note

###### 3.15.1.2.3.1.b (Requirement Type)
Linking
- WordTraceId: 239087
- atomic: true
- Legal Obligation: unknown
- implement: false
- ListNumberText: b)
- kind: Note

###### 3.15.1.2.3.1.c (Requirement Type)
International static speed profiles
- WordTraceId: 239095
- atomic: true
- Legal Obligation: unknown
- implement: false
- ListNumberText: c)
- kind: Note

###### 3.15.1.2.3.1.d (Requirement Type)
Axle Load Speed profiles
- WordTraceId: 239131
- atomic: true
- Legal Obligation: unknown
- implement: false
- ListNumberText: d)
- kind: Note

###### 3.15.1.2.3.1.e (Requirement Type)
Gradients
- WordTraceId: 239156
- atomic: true
- Legal Obligation: unknown
- implement: false
- ListNumberText: e)
- kind: Note

###### 3.15.1.2.3.1.f (Requirement Type)
Temporary speed restrictions
- WordTraceId: 239166
- atomic: true
- Legal Obligation: unknown
- implement: false
- ListNumberText: f)
- kind: Note

###### 3.15.1.2.3.1.g (Requirement Type)
Mode profiles
- WordTraceId: 239195
- atomic: true
- Legal Obligation: unknown
- implement: false
- ListNumberText: g)
- kind: Note

###### 3.15.1.2.3.1.h (Requirement Type)
Intentionally deleted
- WordTraceId: 239209
- atomic: false
- Legal Obligation: not applicable
- implement: false
- ListNumberText: h)
- kind: Placeholder

###### 3.15.1.2.3.1.i (Requirement Type)
Track Conditions
- WordTraceId: 239231
- atomic: true
- Legal Obligation: unknown
- implement: false
- ListNumberText: i)
- kind: Note

###### 3.15.1.2.3.1.j (Requirement Type)
Level Transition orders
- WordTraceId: 239248
- atomic: true
- Legal Obligation: unknown
- implement: false
- ListNumberText: j)
- kind: Note

###### 3.15.1.2.3.1.k (Requirement Type)
Intentionally deleted
- WordTraceId: 239272
- atomic: false
- Legal Obligation: not applicable
- implement: false
- ListNumberText: k)
- kind: Placeholder

###### 3.15.1.2.3.1.l (Requirement Type)
Route Suitability Data
- WordTraceId: 239294
- atomic: true
- Legal Obligation: unknown
- implement: false
- ListNumberText: l)
- kind: Note

###### 3.15.1.2.3.1.m (Requirement Type)
National Values
- WordTraceId: 239317
- atomic: true
- Legal Obligation: unknown
- implement: false
- ListNumberText: m)
- kind: Note

###### 3.15.1.2.3.1.n (Requirement Type)
Adhesion Factor
- WordTraceId: 239334
- atomic: true
- Legal Obligation: unknown
- implement: false
- ListNumberText: n)
- kind: Note

###### 3.15.1.2.3.1.o (Requirement Type)
Level Crossings
- WordTraceId: 239350
- atomic: true
- Legal Obligation: unknown
- implement: false
- ListNumberText: o)
- kind: Note

###### 3.15.1.2.3.1.p (Requirement Type)
Permitted Braking Distance Information
- WordTraceId: 239366
- atomic: true
- Legal Obligation: unknown
- implement: false
- ListNumberText: p)
- kind: Note

###### 3.15.1.2.3.2 (Requirement Type)
Note: The amount of information to be sent between the RBCs is depending on the implementation trackside.
- WordTraceId: 239405
- atomic: false
- Legal Obligation: not applicable
- implement: false
- implementerEnhanced: Note: The amount of information to be sent between the RBCs is depending on the implementation
  trackside
  [EXTERNAL]
  .
- kind: Note

###### 3.15.1.2.4 (Requirement Type)
Note: Route related information received from the Accepting RBC will be processed by the Handing Over RBC if possible.
- WordTraceId: 239511
- atomic: false
- Legal Obligation: not applicable
- implement: false
- implementerEnhanced: Note: Route related information received from the Accepting
  RBC
  [EXTERNAL]
  will be processed by the Handing Over
  RBC
  [EXTERNAL]
  if
  [CONDITION]
  possible
  [WEAK]
  .
- kind: Note

###### 3.15.1.2.5 (Requirement Type)
Deleted.
- WordTraceId: 239630
- atomic: false
- Legal Obligation: not applicable
- implement: false
- kind: Placeholder

###### 3.15.1.2.6 (Requirement Type)
When the Handing Over RBC receives a position report and detects that the maximum safe front end of the train has passed the border location, it shall inform the Accepting RBC.
- WordTraceId: 239640
- atomic: true
- Legal Obligation: mandatory
- implement: true
- implementerEnhanced: When
  [CONDITION]
  the Handing Over
  RBC
  [EXTERNAL]
  receives a position report and detects that the maximum safe front end of the train has passed the border location, it shall inform the Accepting
  RBC
  [EXTERNAL]
  .
- kind: ordinary

###### 3.15.1.2.6.1 (Requirement Type)
Note: This information might be needed to inform the signalman of the Accepting RBC that the train has entered the Accepting RBC area.
- WordTraceId: 239817
- atomic: false
- Legal Obligation: not applicable
- implement: false
- implementerEnhanced: Note: This information might be needed to inform the
  signalman
  [EXTERNAL]
  of the Accepting
  RBC
  [EXTERNAL]
  that the train has entered the Accepting
  RBC
  [EXTERNAL]
  area.
- kind: Note

###### 3.15.1.2.7 (Requirement Type)
When the Handing Over RBC receives a position report and detects that the minimum safe rear end of the train has crossed the border, it shall send a disconnection order to the on-board equipment.
- WordTraceId: 239952
- atomic: true
- Legal Obligation: mandatory
- implement: true
- implementerEnhanced: When
  [CONDITION]
  the Handing Over
  RBC
  [EXTERNAL]
  receives a position report and detects that the minimum safe rear end of the train has crossed the border, it shall send a disconnection order to the
  on-board equipment
  [SELF]
  .
- kind: ordinary

###### 3.15.1.2.8 (Requirement Type)
When the Accepting RBC informs the Handing Over RBC that it has taken over the responsibility, the latter shall stop sending route related information to the on-board equipment.
- WordTraceId: 240148
- atomic: true
- Legal Obligation: mandatory
- implement: true
- implementerEnhanced: When
  [CONDITION]
  the Accepting
  RBC
  [EXTERNAL]
  informs the Handing Over
  RBC
  [EXTERNAL]
  that it has taken over the responsibility, the latter shall stop sending route related information to the
  on-board equipment
  [SELF]
  .
- kind: ordinary

###### 3.15.1.2.9 (Requirement Type)
When the Handing Over RBC detects that the transition to the Accepting RBC has to be cancelled, it shall send this cancellation information to the Accepting RBC (including the train identification).
- WordTraceId: 240327
- atomic: true
- Legal Obligation: mandatory
- implement: true
- implementerEnhanced: When
  [CONDITION]
  the Handing Over
  RBC
  [EXTERNAL]
  detects that the transition to the Accepting
  RBC
  [EXTERNAL]
  has to be cancelled, it shall send this cancellation information to the Accepting
  RBC
  [EXTERNAL]
  (including the train identification).
- kind: ordinary

###### 3.15.1.2.9.1 (Requirement Type)
Note: For instance, the cancellation procedure can be triggered by:
- WordTraceId: 240526
- atomic: false
- Legal Obligation: not applicable
- implement: false
- kind: Note

###### 3.15.1.2.9.1.*[1] (Requirement Type)
Change to a route which does no more include the border;
- WordTraceId: 240595
- atomic: true
- Legal Obligation: unknown
- implement: false
- ListNumberText: ·
- kind: Note

###### 3.15.1.2.9.1.*[2] (Requirement Type)
The sending of an “end of mission” information from the on-board equipment.
- WordTraceId: 240652
- atomic: true
- Legal Obligation: unknown
- implement: false
- implementerEnhanced: The sending of an “end of mission” information from the
  on-board equipment
  [SELF]
  .
- ListNumberText: ·
- kind: Note

##### 3.15.1.3 (Requirement Type)
On-board equipment
- WordTraceId: 240728
- atomic: false
- Legal Obligation: not applicable
- implement: false
- implementerEnhanced: On-board equipment
  [SELF]
- kind: Heading

###### 3.15.1.3.1 (Requirement Type)
When receiving an order to switch to another RBC at a given location, the on-board equipment shall:
- WordTraceId: 240747
- atomic: true
- Legal Obligation: not applicable
- implement: false
- implementerEnhanced: When
  [CONDITION]
  receiving an order to switch to another
  RBC
  [EXTERNAL]
  at a given location, the
  on-board equipment
  [SELF]
  shall:
- kind: Heading

###### 3.15.1.3.1.a (Requirement Type)
Establish the communication session with the Accepting RBC;
- WordTraceId: 240847
- atomic: true
- Legal Obligation: mandatory
- implement: true
- implementerEnhanced: Establish the communication session with the Accepting
  RBC
  [EXTERNAL]
  ;
- ListNumberText: a)
- kind: ordinary

###### 3.15.1.3.1.b (Requirement Type)
Send a position report to the Handing Over RBC when the maximum safe front end of the train passes the given location;
- WordTraceId: 240907
- atomic: true
- Legal Obligation: mandatory
- implement: true
- implementerEnhanced: Send a position report to the Handing Over
  RBC
  [EXTERNAL]
  when
  [CONDITION]
  the maximum safe front end of the train passes the given location;
- ListNumberText: b)
- kind: ordinary

###### 3.15.1.3.1.c (Requirement Type)
Send a position report to the Handing Over RBC when the minimum safe rear end of the train passes the given location;
- WordTraceId: 241026
- atomic: true
- Legal Obligation: mandatory
- implement: true
- implementerEnhanced: Send a position report to the Handing Over
  RBC
  [EXTERNAL]
  when
  [CONDITION]
  the minimum safe rear end of the train passes the given location;
- ListNumberText: c)
- kind: ordinary

###### 3.15.1.3.2 (Requirement Type)
It is up to the on-board equipment to manage the establishment of one communication session and the release of the other one:
- WordTraceId: 241144
- atomic: true
- Legal Obligation: unknown
- implement: false
- implementerEnhanced: It is up to the
  on-board equipment
  [SELF]
  to manage the establishment of one communication session and the release of the other one:
- kind: Heading

###### 3.15.1.3.2.a (Requirement Type)
If it is able to handle two communication sessions at the same time, the radio session with the Accepting RBC shall be established as soon as it receives the RBC transition order .
- WordTraceId: 241270
- atomic: true
- Legal Obligation: mandatory
- implement: true
- implementerEnhanced: If
  [CONDITION]
  it is able to handle two communication sessions at the same
  time
  [TIME]
  , the radio session with the Accepting
  RBC
  [EXTERNAL]
  shall be established
  as soon as
  [WEAK]
  it receives the
  RBC
  [EXTERNAL]
  transition order .
- ListNumberText: a)
- kind: ordinary

###### 3.15.1.3.2.b (Requirement Type)
If it is able to handle one communication session only at a given time, it shall wait until the session with the Handing over RBC is terminated due to crossing the border (refer to 3.5.5.1e and 3.15.1.2.7) and then establish the session with the Accepting RBC.
- WordTraceId: 241451
- atomic: true
- Legal Obligation: mandatory
- implement: true
- implementerEnhanced: If
  [CONDITION]
  it is able to handle one communication session only at a given
  time
  [TIME]
  , it shall
  wait
  [TIME]
  until
  [TIME]
  the session with the Handing over
  RBC
  [EXTERNAL]
  is terminated due to crossing the border (refer to 3.5.5.1e and 3.15.1.2.7) and then establish the session with the Accepting
  RBC
  [EXTERNAL]
  .
- ListNumberText: b)
- kind: ordinary
- CrossRefLink -> 3.5.5.1.e
- CrossRefLink -> 3.15.1.2.7

###### 3.15.1.3.3 (Requirement Type)
As soon as the on-board equipment has established the session with the Accepting RBC, it shall send its Train Data unless it is in sleeping or non leading mode.
- WordTraceId: 241712
- atomic: true
- Legal Obligation: mandatory
- implement: true
- implementerEnhanced: As soon as
  [WEAK]
  the
  on-board equipment
  [SELF]
  has established the session with the Accepting
  RBC
  [EXTERNAL]
  , it shall send its Train Data unless it is in sleeping or non leading mode.
- kind: ordinary

###### 3.15.1.3.4 (Requirement Type)
When the on-board equipment is connected to both RBCs, it shall send its position reports to both of them with the use of the position report parameters valid for the Handing Over RBC.
- WordTraceId: 241873
- atomic: true
- Legal Obligation: mandatory
- implement: true
- implementerEnhanced: When
  [CONDITION]
  the
  on-board equipment
  [SELF]
  is connected to both RBCs, it shall send its position reports to both of them with the use of the position report parameters valid for the Handing Over
  RBC
  [EXTERNAL]
  .
- kind: ordinary

###### 3.15.1.3.4.1 (Requirement Type)
If the on-board equipment is connected to both RBCs, and it executes an End of Mission, it shall execute the End of Mission procedure with both RBCs
- WordTraceId: 242058
- atomic: true
- Legal Obligation: mandatory
- implement: true
- implementerEnhanced: If
  [CONDITION]
  the
  on-board equipment
  [SELF]
  is connected to both RBCs, and it executes an
  End of Mission
  [LINKED_PHRASE]
  , it shall execute the
  End of Mission
  [LINKED_PHRASE]
  procedure with both RBCs
- kind: ordinary
- KnownTermLink -> 3.15.1.2.9.1.*[2]

###### 3.15.1.3.5 (Requirement Type)
When the on-board sends a position report directly to the Accepting RBC with its maximum safe front end having passed the border, it shall use information received from the Accepting RBC and only a disconnection order shall be accepted from the Handing Over RBC.
- WordTraceId: 242207
- atomic: false
- Legal Obligation: mandatory
- implement: true
- implementerEnhanced: When
  [CONDITION]
  the on-board sends a position report directly to the Accepting
  RBC
  [EXTERNAL]
  with its maximum safe front end having passed the border, it shall use information received from the Accepting
  RBC
  [EXTERNAL]
  and only a disconnection order shall be accepted from the Handing Over
  RBC
  [EXTERNAL]
  .
- kind: ordinary

###### 3.15.1.3.5.1 (Requirement Type)
Note: This requirement implies that the connection to the Accepting RBC and that the determination of the version have been achieved and that the on-board is able to handle two communication sessions at the same time.
- WordTraceId: 242470
- atomic: false
- Legal Obligation: not applicable
- implement: false
- implementerEnhanced: Note: This requirement implies that the connection to the Accepting
  RBC
  [EXTERNAL]
  and that the determination of the version have been achieved and that the on-board is able to handle two communication sessions at the same
  time
  [TIME]
  .
- kind: Note

###### 3.15.1.3.6 (Requirement Type)
In case two communication sessions are opened, if information is received from the Accepting RBC before a position report is sent to the Accepting RBC with the maximum safe front end having passed the border, this information shall be stored on-board.
Exception: The acknowledgement of Train Data shall be immediately accepted by the on-board equipment.
- WordTraceId: 242688
- atomic: false
- Legal Obligation: mandatory
- implement: true
- implementerEnhanced: In case
  [CONDITION]
  two communication sessions are opened,
  if
  [CONDITION]
  information is received from the Accepting
  RBC
  [EXTERNAL]
  before a position report is sent to the Accepting
  RBC
  [EXTERNAL]
  with the maximum safe front end having passed the border, this information shall be stored on-board. Exception: The acknowledgement of Train Data shall be
  immediately
  [WEAK]
  accepted by the
  on-board equipment
  [SELF]
  .
- kind: ordinary

###### 3.15.1.3.6.1 (Requirement Type)
Note: for the exhaustive list of accepted/rejected information, please refer to Chapter 4 Use of received information.
- WordTraceId: 243043
- atomic: false
- Legal Obligation: not applicable
- implement: false
- kind: Note

###### 3.15.1.3.7 (Requirement Type)
Intentionally deleted.
- WordTraceId: 243163
- atomic: false
- Legal Obligation: not applicable
- implement: false
- kind: Placeholder

##### 3.15.1.4 (Requirement Type)
Accepting RBC
- WordTraceId: 243186
- atomic: false
- Legal Obligation: not applicable
- implement: false
- implementerEnhanced: Accepting
  RBC
  [EXTERNAL]
- kind: Heading

###### 3.15.1.4.1 (Requirement Type)
The Accepting RBC shall keep route related information sent to the Handing Over RBC updated. In particular, this possibly includes temporary speed restrictions.
- WordTraceId: 243200
- atomic: false
- Legal Obligation: mandatory
- implement: true
- implementerEnhanced: The Accepting
  RBC
  [EXTERNAL]
  shall keep route related information sent to the Handing Over
  RBC
  [EXTERNAL]
  updated. In particular, this
  possibly
  [WEAK]
  includes temporary speed restrictions.
- kind: ordinary

###### 3.15.1.4.2 (Requirement Type)
As soon as the Accepting RBC receives from the on-board equipment a position report and detects that the maximum safe front end of the train has passed the border, it shall inform the Handing Over RBC that it has taken over the responsibility.
- WordTraceId: 243361
- atomic: true
- Legal Obligation: mandatory
- implement: true
- implementerEnhanced: As soon as
  [WEAK]
  the Accepting
  RBC
  [EXTERNAL]
  receives from the
  on-board equipment
  [SELF]
  a position report and detects that the maximum safe front end of the train has passed the border, it shall inform the Handing Over
  RBC
  [EXTERNAL]
  that it has taken over the responsibility.
- kind: ordinary

###### 3.15.1.4.3 (Requirement Type)
When the Accepting RBC receives Train Data from both the on-board equipment and the Handing over RBC Train Data provided by the on-board equipment shall take precedence.
- WordTraceId: 243605
- atomic: true
- Legal Obligation: mandatory
- implement: true
- implementerEnhanced: When
  [CONDITION]
  the Accepting
  RBC
  [EXTERNAL]
  receives Train Data from both the
  on-board equipment
  [SELF]
  and the Handing over
  RBC
  [EXTERNAL]
  Train Data provided by the
  on-board equipment
  [SELF]
  shall take precedence.
- kind: ordinary

###### 3.15.1.4.4 (Requirement Type)
If the Accepting RBC receives a cancellation information from the Handing Over RBC, it shall send an order to terminate the communication session to the corresponding on-board equipment (if already established).
- WordTraceId: 243775
- atomic: true
- Legal Obligation: mandatory
- implement: true
- implementerEnhanced: If
  [CONDITION]
  the Accepting
  RBC
  [EXTERNAL]
  receives a cancellation information from the Handing Over
  RBC
  [EXTERNAL]
  , it shall send an order to
  terminate the communication session
  [LINKED_PHRASE]
  to the corresponding
  on-board equipment
  [SELF]
  (
  if
  [CONDITION]
  already established).
- kind: ordinary
- KnownTermLink -> 3.5.4.3.*[3]

###### 3.15.1.4.5 (Requirement Type)
The Accepting RBC shall comply with the maximum amount of data contained in the last received route related information request from the Handing Over RBC.
- WordTraceId: 243987
- atomic: true
- Legal Obligation: mandatory
- implement: true
- implementerEnhanced: The Accepting
  RBC
  [EXTERNAL]
  shall comply with the maximum amount of data contained in the last received route related information request from the Handing Over
  RBC
  [EXTERNAL]
  .
- kind: ordinary

##### 3.15.1.5 (Requirement Type)
RBC/RBC message acknowledgement
- WordTraceId: 244142
- atomic: false
- Legal Obligation: not applicable
- implement: false
- implementerEnhanced: RBC
  [EXTERNAL]
  /
  RBC
  [EXTERNAL]
  message acknowledgement
- kind: Heading

###### 3.15.1.5.1 (Requirement Type)
As soon as a consistent RBC/RBC message including the request for acknowledgement is received, the receiving RBC shall send an acknowledgement to the emitting RBC.
- WordTraceId: 244174
- atomic: true
- Legal Obligation: mandatory
- implement: true
- implementerEnhanced: As soon as
  [WEAK]
  a consistent
  RBC
  [EXTERNAL]
  /
  RBC
  [EXTERNAL]
  message including the request for acknowledgement is received, the receiving
  RBC
  [EXTERNAL]
  shall send an acknowledgement to the emitting
  RBC
  [EXTERNAL]
  .
- kind: ordinary

###### 3.15.1.5.2 (Requirement Type)
The RBC/RBC message is consistent when all checks have been completed successfully:
- WordTraceId: 244338
- atomic: true
- Legal Obligation: unknown
- implement: false
- implementerEnhanced: The
  RBC
  [EXTERNAL]
  /
  RBC
  [EXTERNAL]
  message is consistent
  when
  [CONDITION]
  all checks have been completed successfully:
- kind: Heading

###### 3.15.1.5.2.a (Requirement Type)
It has passed the checks performed by the RBC/RBC Safe Communication Interface protocol (see SUBSET-098);
- WordTraceId: 244422
- atomic: true
- Legal Obligation: unknown
- implement: true
- implementerEnhanced: It has passed the checks performed by the
  RBC
  [EXTERNAL]
  /
  RBC
  [EXTERNAL]
  Safe Communication Interface protocol (see SUBSET-098);
- ListNumberText: a)
- kind: ordinary

###### 3.15.1.5.2.b (Requirement Type)
Variables in the message do not have invalid values.
- WordTraceId: 244528
- atomic: true
- Legal Obligation: unknown
- implement: true
- ListNumberText: b)
- kind: ordinary

###### 3.15.1.5.3 (Requirement Type)
The acknowledgement message shall refer to the identity of the concerned message sent by the emitting RBC.
- WordTraceId: 244581
- atomic: true
- Legal Obligation: mandatory
- implement: true
- implementerEnhanced: The acknowledgement message shall refer to the identity of the concerned message sent by the emitting
  RBC
  [EXTERNAL]
  .
- kind: ordinary

#### 3.15.2 (Requirement Type)
Handling of Trains with Non Leading Engines
- WordTraceId: 244688
- atomic: false
- Legal Obligation: not applicable
- implement: false
- kind: Heading

##### 3.15.2.1 (Requirement Type)
It shall be possible to operate a train using more than one engine, each engine being under the control of a driver.
- WordTraceId: 244732
- atomic: true
- Legal Obligation: mandatory
- implement: true
- implementerEnhanced: It shall be possible to operate a train using more than one engine, each engine being under the control of a
  driver
  [EXTERNAL]
  .
- kind: ordinary

##### 3.15.2.2 (Requirement Type)
Only the leading engine shall be responsible for the train movement supervision functions.
- WordTraceId: 244851
- atomic: true
- Legal Obligation: mandatory
- implement: true
- kind: ordinary

#### 3.15.3 (Requirement Type)
Splitting/joining
- WordTraceId: 244942
- atomic: false
- Legal Obligation: not applicable
- implement: false
- kind: Heading

##### 3.15.3.1 (Requirement Type)
ERTMS/ETCS shall allow Splitting and Joining using the normal supervision functions available (e.g. On-sight, Shunting).
- WordTraceId: 244960
- atomic: false
- Legal Obligation: mandatory
- implement: true
- implementerEnhanced: ERTMS/ETCS shall allow Splitting and Joining using the normal supervision functions available (
  e.g.
  [WEAK]
  On-sight, Shunting).
- kind: ordinary

##### 3.15.3.2 (Requirement Type)
Splitting only refers to the case that the two resulting trains contain at least one ERTMS/ETCS on-board equipment each.
- WordTraceId: 245081
- atomic: true
- Legal Obligation: unknown
- implement: true
- implementerEnhanced: Splitting only refers to the case that the two resulting trains contain
  at least
  [WEAK]
  one
  ERTMS/ETCS on-board equipment
  [SELF]
  each.
- kind: ordinary

###### 3.15.3.2.1 (Requirement Type)
Note: This must be ensured by operational procedures.
- WordTraceId: 245202
- atomic: false
- Legal Obligation: not applicable
- implement: false
- kind: Note

##### 3.15.3.3 (Requirement Type)
ERTMS/ETCS is not responsible for providing information that a Splitting/Joining operation has been correctly completed (technical aspect and/or operational aspect).
- WordTraceId: 245256
- atomic: true
- Legal Obligation: unknown
- implement: true
- kind: ordinary

##### 3.15.3.4 (Requirement Type)
Justification: ERTMS/ETCS is not able to provide this information. Splitting and Joining shall require the fulfilment of operating rules ensuring that a Splitting/Joining operation has been correctly completed (e.g. physical disconnection).
- WordTraceId: 245422
- atomic: false
- Legal Obligation: mandatory
- implement: false
- implementerEnhanced: Justification: ERTMS/ETCS is not able to provide this information. Splitting and Joining shall require the fulfilment of operating rules ensuring that a Splitting/Joining operation has been correctly completed (
  e.g.
  [WEAK]
  physical disconnection).
- kind: Justification

#### 3.15.4 (Requirement Type)
Reversing of movement direction
- WordTraceId: 245663
- atomic: false
- Legal Obligation: not applicable
- implement: false
- kind: Heading

##### 3.15.4.1 (Requirement Type)
It shall be possible to send in advance to an on-board equipment information about areas, where initiation of reversing of movement direction is possible, i.e. change the direction of train movement without changing the train orientation.
- WordTraceId: 245695
- atomic: true
- Legal Obligation: mandatory
- implement: true
- implementerEnhanced: It shall be possible to send in advance to an
  on-board equipment
  [SELF]
  information about areas, where initiation of reversing of movement direction is possible, i.e. change the direction of train movement without changing the train orientation.
- kind: ordinary

###### 3.15.4.1.1 (Requirement Type)
A new reversing area given from the trackside shall replace the one already available on-board.
- WordTraceId: 245934
- atomic: true
- Legal Obligation: mandatory
- implement: true
- implementerEnhanced: A new reversing area given from the
  trackside
  [EXTERNAL]
  shall replace the one already available on-board.
- kind: ordinary

##### 3.15.4.2 (Requirement Type)
Together with start and end of reversing area, the following supervision information shall be sent:
- WordTraceId: 246030
- atomic: true
- Legal Obligation: mandatory
- implement: true
- kind: ordinary

###### 3.15.4.2.a (Requirement Type)
Maximum distance to run in the direction opposite to the orientation of the reversing area, the fixed reference location being the end location of the area where reversing of movement is permitted at the time of reception of this reversing area information.
- WordTraceId: 246130
- atomic: true
- Legal Obligation: mandatory
- implement: true
- implementerEnhanced: Maximum distance to run in the direction opposite to the orientation of the reversing area, the fixed reference location being the end location of the area where reversing of movement is permitted at the
  time
  [TIME]
  of reception of this reversing area information.
- ListNumberText: a)
- kind: ordinary

###### 3.15.4.2.b (Requirement Type)
Reversing mode speed limit allowed during reverse movement.
- WordTraceId: 246388
- atomic: true
- Legal Obligation: mandatory
- implement: true
- implementerEnhanced: Reversing mode speed limit allowed
  during
  [TIME]
  reverse movement.
- ListNumberText: b)
- kind: ordinary

##### 3.15.4.2[2] (Requirement Type)
- WordTraceId: 246448
- atomic: false
- Legal Obligation: not applicable
- implement: false
- kind: Placeholder

###### 3.15.4.2[2].[f]57 (Requirement Type)
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- WordTraceId: 246473
- atomic: false
- Legal Obligation: not applicable
- implement: false
- kind: Figure

###### 3.15.4.2[2].[f]57.C (Requirement Type)
Figure {Figure 57}: Reversing area and maximum distance to run
- WordTraceId: 246473
- atomic: true
- Legal Obligation: unknown
- PlainText: Figure 57: Reversing area and maximum distance to run
- implement: false
- kind: Figure

###### 3.15.4.2[2].1 (Requirement Type)
Note: If a closer SvL is defined, see Appendix 3.4 for a complete list of situations, the reversing area is deleted beyond the new SvL. The reference location for the distance to run in the direction opposite to the reversing area remains fixed at its original position.
- WordTraceId: 246552
- atomic: false
- Legal Obligation: not applicable
- implement: false
- implementerEnhanced: Note:
  If
  [CONDITION]
  a closer SvL is defined, see Appendix 3.4 for a complete list of situations, the reversing area is deleted beyond the new SvL. The reference location for the distance to run in the direction opposite to the reversing area remains fixed at its original position.
- ListNumberText: 3.15.4.2.1
- kind: Note
- CrossRefLink -> A.3.4

###### 3.15.4.2[2].1[2] (Requirement Type)
- WordTraceId: 246823
- atomic: false
- Legal Obligation: not applicable
- implement: false
- kind: Placeholder

###### 3.15.4.2[2].1[2].[f]58 (Requirement Type)
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- WordTraceId: 246848
- atomic: false
- Legal Obligation: not applicable
- implement: false
- kind: Figure

###### 3.15.4.2[2].1[2].[f]58.C (Requirement Type)
Figure {Figure 58}: Influence of a shortened Movement Authority
- WordTraceId: 246848
- atomic: true
- Legal Obligation: unknown
- PlainText: Figure 58: Influence of a shortened Movement Authority
- implement: false
- kind: Figure

###### 3.15.4.2[2].2 (Requirement Type)
Note: All locations refer to the estimated front end of the train (refer to clause 3.6.4.6).
- WordTraceId: 246928
- atomic: false
- Legal Obligation: not applicable
- implement: false
- ListNumberText: 3.15.4.2.2
- kind: Note
- CrossRefLink -> 3.6.4.6

##### 3.15.4.3 (Requirement Type)
New distance to run and Reversing mode speed limit given from the trackside shall replace the one already available on-board.
- WordTraceId: 247021
- atomic: true
- Legal Obligation: mandatory
- implement: true
- implementerEnhanced: New distance to run and Reversing mode speed limit given from the
  trackside
  [EXTERNAL]
  shall replace the one already available on-board.
- kind: ordinary

###### 3.15.4.3.1 (Requirement Type)
In case of update of distance to run in reverse movement, the fixed reference location for reversing distance shall remain unchanged.
- WordTraceId: 247148
- atomic: true
- Legal Obligation: mandatory
- implement: true
- implementerEnhanced: In case of
  [CONDITION]
  update of distance to run in reverse movement, the fixed reference location for reversing distance shall remain unchanged.
- kind: ordinary

###### 3.15.4.3.1[2] (Requirement Type)
- WordTraceId: 247282
- atomic: false
- Legal Obligation: not applicable
- implement: false
- kind: Placeholder

###### 3.15.4.3.1[2].[f]59 (Requirement Type)
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- WordTraceId: 247307
- atomic: false
- Legal Obligation: not applicable
- implement: false
- kind: Figure

###### 3.15.4.3.1[2].[f]59.C (Requirement Type)
Figure {Figure 59}: New maximum distance to run
- WordTraceId: 247307
- atomic: true
- Legal Obligation: unknown
- PlainText: Figure 59: New maximum distance to run
- implement: false
- implementerEnhanced: Figure 59: New maximum distance to run
- kind: Figure

##### 3.15.4.4 (Requirement Type)
While at standstill with the front end of the train inside the indicated area, it shall be possible for the driver to reverse the direction of movement.
- WordTraceId: 247371
- atomic: true
- Legal Obligation: mandatory
- implement: true
- implementerEnhanced: While
  [TIME]
  at standstill with the front end of the train inside the indicated area, it shall be possible for the
  driver
  [EXTERNAL]
  to reverse the direction of movement.
- kind: ordinary

##### 3.15.4.5 (Requirement Type)
The on-board equipment shall allow movement in the direction opposite to the train orientation, supervising it according to distance and speed received.
- WordTraceId: 247524
- atomic: true
- Legal Obligation: mandatory
- implement: true
- implementerEnhanced: The
  on-board equipment
  [SELF]
  shall allow movement in the direction opposite to the train orientation, supervising it according to distance and speed received.
- kind: ordinary

##### 3.15.4.6 (Requirement Type)
Note: level transitions and RBC/RBC handovers are not handled by the ERTMS/ETCS on-board equipment when in Reversing mode.
- WordTraceId: 247677
- atomic: false
- Legal Obligation: not applicable
- implement: false
- implementerEnhanced: Note: level transitions and
  RBC
  [EXTERNAL]
  /
  RBC
  [EXTERNAL]
  handovers are not handled by the
  ERTMS/ETCS on-board equipment
  [SELF]
  when
  [CONDITION]
  in Reversing mode.
- kind: Note

##### 3.15.4.7 (Requirement Type)
When at standstill the on-board equipment shall inform the driver if the reversing of movement is permitted.
- WordTraceId: 247800
- atomic: true
- Legal Obligation: mandatory
- implement: true
- implementerEnhanced: When
  [CONDITION]
  at standstill the
  on-board equipment
  [SELF]
  shall inform the
  driver
  [EXTERNAL]
  if
  [CONDITION]
  the reversing of movement is permitted.
- kind: ordinary

##### 3.15.4.8 (Requirement Type)
If the end location of the maximum distance to run in the opposite direction is passed by the train front end, the emergency brake command shall be triggered.
- WordTraceId: 247909
- atomic: true
- Legal Obligation: mandatory
- implement: true
- implementerEnhanced: If
  [CONDITION]
  the end location of the maximum distance to run in the opposite direction is passed by the train front end, the emergency brake command shall be triggered.
- kind: ordinary

#### 3.15.5 (Requirement Type)
Track ahead free
- WordTraceId: 248068
- atomic: false
- Legal Obligation: not applicable
- implement: false
- kind: Heading

##### 3.15.5.1 (Requirement Type)
In a level 2/3 area, the ERTMS/ETCS on-board equipment shall be able to handle a track ahead free request given by the RBC.
- WordTraceId: 248085
- atomic: true
- Legal Obligation: mandatory
- implement: true
- implementerEnhanced: In a level 2/3 area, the
  ERTMS/ETCS on-board equipment
  [SELF]
  shall be able to handle a track ahead free request given by the
  RBC
  [EXTERNAL]
  .
- kind: ordinary

##### 3.15.5.2 (Requirement Type)
The track ahead free request from the RBC shall indicate to the on-board
- WordTraceId: 248209
- atomic: true
- Legal Obligation: mandatory
- implement: true
- implementerEnhanced: The track ahead free request from the
  RBC
  [EXTERNAL]
  shall indicate to the on-board
- kind: ordinary

###### 3.15.5.2.a (Requirement Type)
at which location the ERTMS/ETCS on-board equipment shall begin to display the request to the driver.
- WordTraceId: 248282
- atomic: true
- Legal Obligation: mandatory
- implement: true
- implementerEnhanced: at which location the
  ERTMS/ETCS on-board equipment
  [SELF]
  shall begin to display the request to the
  driver
  [EXTERNAL]
  .
- ListNumberText: a)
- kind: ordinary

###### 3.15.5.2.b (Requirement Type)
at which location the ERTMS/ETCS on-board equipment shall stop to display the request to the driver (in case the driver did not acknowledge).
- WordTraceId: 248384
- atomic: true
- Legal Obligation: mandatory
- implement: true
- implementerEnhanced: at which location the
  ERTMS/ETCS on-board equipment
  [SELF]
  shall stop to display the request to the
  driver
  [EXTERNAL]
  (
  in case
  [CONDITION]
  the
  driver
  [EXTERNAL]
  did not acknowledge).
- ListNumberText: b)
- kind: ordinary

##### 3.15.5.3 (Requirement Type)
The driver shall have the possibility to acknowledge the track ahead free request (meaning the driver confirms that the track between the head of the train and the next signal or board marking signal position is free).
- WordTraceId: 248526
- atomic: true
- Legal Obligation: mandatory
- implement: true
- implementerEnhanced: The
  driver
  [EXTERNAL]
  shall have the possibility to acknowledge the track ahead free request (meaning the
  driver
  [EXTERNAL]
  confirms that the track between the head of the train and the next signal or board marking signal position is free).
- kind: ordinary

##### 3.15.5.4 (Requirement Type)
When the driver acknowledges, the ERTMS/ETCS on-board equipment shall stop displaying the request, and shall inform the RBC that the track ahead is free.
- WordTraceId: 248745
- atomic: false
- Legal Obligation: mandatory
- implement: true
- implementerEnhanced: When
  [CONDITION]
  the
  driver
  [EXTERNAL]
  acknowledges, the
  ERTMS/ETCS on-board equipment
  [SELF]
  shall stop displaying the request, and shall inform the
  RBC
  [EXTERNAL]
  that the track ahead is free.
- kind: ordinary

##### 3.15.5.5 (Requirement Type)
There shall be no restrictive consequence by the on-board system if the driver does not acknowledge.
- WordTraceId: 248899
- atomic: true
- Legal Obligation: mandatory
- implement: true
- implementerEnhanced: There shall be no restrictive consequence by the on-board system
  if
  [CONDITION]
  the
  driver
  [EXTERNAL]
  does not acknowledge.
- kind: ordinary

##### 3.15.5.6 (Requirement Type)
A new track ahead free request shall replace the one previously received and stored.
- WordTraceId: 249000
- atomic: true
- Legal Obligation: mandatory
- implement: true
- kind: ordinary

#### 3.15.6 (Requirement Type)
Handling of National Systems
- WordTraceId: 249085
- atomic: false
- Legal Obligation: not applicable
- implement: false
- kind: Heading

##### 3.15.6.1 (Requirement Type)
The ERTMS/ETCS on-board shall support driving on national infrastructure under the supervision of National Systems.
- WordTraceId: 249114
- atomic: true
- Legal Obligation: mandatory
- implement: true
- implementerEnhanced: The
  ERTMS/ETCS on-board
  [SELF]
  shall support driving on national infrastructure under the supervision of National Systems.
- kind: ordinary

##### 3.15.6.2 (Requirement Type)
In case the ERTMS/ETCS on-board equipment is interfaced to a National System through an STM, refer to Subset 035 for detailed requirements.
- WordTraceId: 249230
- atomic: true
- Legal Obligation: unknown
- implement: true
- implementerEnhanced: In case
  [CONDITION]
  the
  ERTMS/ETCS on-board equipment
  [SELF]
  is interfaced to a
  National System
  [EXTERNAL]
  through an STM, refer to Subset 035 for detailed requirements.
- kind: ordinary

###### 3.15.6.2.1 (Requirement Type)
Intentionally deleted.
- WordTraceId: 249370
- atomic: false
- Legal Obligation: not applicable
- implement: false
- kind: Placeholder

##### 3.15.6.3 (Requirement Type)
Intentionally deleted.
- WordTraceId: 249394
- atomic: false
- Legal Obligation: not applicable
- implement: false
- kind: Placeholder

##### 3.15.6.4 (Requirement Type)
Intentionally deleted.
- WordTraceId: 249418
- atomic: false
- Legal Obligation: not applicable
- implement: false
- kind: Placeholder

##### 3.15.6.5 (Requirement Type)
Amongst the data to be used by applications outside ERTMS/ETCS that can be transmitted by trackside over the ERTMS/ETCS transmission channels, it shall be possible to send from balises or RBC data to be forwarded to a National System.
- WordTraceId: 249442
- atomic: true
- Legal Obligation: mandatory
- implement: true
- implementerEnhanced: Amongst the data to be used by applications outside ERTMS/ETCS that can be transmitted by
  trackside
  [EXTERNAL]
  over the ERTMS/ETCS transmission channels, it shall be possible to send from
  balises
  [EXTERNAL]
  or
  RBC
  [EXTERNAL]
  data to be forwarded to a
  National System
  [EXTERNAL]
  .
- kind: ordinary

###### 3.15.6.5.1 (Requirement Type)
Note: Definition of what qualifies as “data to be forwarded to a National System” is national dependent and outside the scope of Subset 026.
- WordTraceId: 249677
- atomic: false
- Legal Obligation: not applicable
- implement: false
- implementerEnhanced: Note: Definition of what qualifies as “data to be forwarded to a
  National System
  [EXTERNAL]
  ” is national dependent and outside the scope of Subset 026.
- kind: Note

#### 3.15.7 (Requirement Type)
Tolerance of Big Metal Mass
- WordTraceId: 249818
- atomic: false
- Legal Obligation: not applicable
- implement: false
- kind: Heading

##### 3.15.7.1 (Requirement Type)
Big metal object in the track, exceeding the limits for big metal masses as defined in Subset-036, section 6.5.2 “Metal Masses in the Track” may trigger an alarm reporting a malfunction for the onboard balise transmission function.
- WordTraceId: 249846
- atomic: true
- Legal Obligation: optional
- implement: true
- implementerEnhanced: Big metal object in the track, exceeding the limits for
  big metal masses
  [LINKED_PHRASE]
  as defined in Subset-036, section 6.5.2 “Metal Masses in the Track” may trigger an alarm reporting a malfunction for the onboard
  balise
  [EXTERNAL]
  transmission function.
- kind: ordinary
- KnownTermLink -> 3.12.1.5.a

##### 3.15.7.2 (Requirement Type)
In Levels 0/NTC, the alarms which may be triggered by metal masses shall be ignored for a defined distance (see A3.1). If the alarm persists for a longer distance the ERTMS/ETCS on-board equipment shall trigger a safety reaction.
- WordTraceId: 250078
- atomic: false
- Legal Obligation: optional
- implement: true
- implementerEnhanced: In Levels 0/NTC, the alarms which may be triggered by metal masses shall be ignored for a defined distance (see A3.1).
  If
  [CONDITION]
  the alarm persists for a longer distance the
  ERTMS/ETCS on-board equipment
  [SELF]
  shall trigger a safety reaction.
- kind: ordinary
- CrossRefLink -> A.3.1

##### 3.15.7.3 (Requirement Type)
Justification: Ignoring the alarm for a defined distance eliminates the need to equip all excessive big metal masses with track condition “Big Metal Mass” outside ETCS fitted areas.
- WordTraceId: 250308
- atomic: false
- Legal Obligation: not applicable
- implement: false
- implementerEnhanced: Justification: Ignoring the alarm for a defined distance eliminates the need to equip all excessive
  big metal masses
  [LINKED_PHRASE]
  with track condition “Big Metal Mass” outside ETCS fitted areas.
- kind: Justification
- KnownTermLink -> 3.12.1.5.a

#### 3.15.8 (Requirement Type)
Cold Movement Detection
- WordTraceId: 250490
- atomic: false
- Legal Obligation: not applicable
- implement: false
- kind: Heading

##### 3.15.8.1 (Requirement Type)
After being switched off (i.e. once in No Power mode), the ERTMS/ETCS on-board equipment shall be capable, if fitted with, to detect and record whether the engine has been moved or not, during a period of at least 72 hours.
- WordTraceId: 250514
- atomic: true
- Legal Obligation: mandatory
- implement: true
- implementerEnhanced: After
  [TIME]
  being switched off (i.e. once in No Power mode), the
  ERTMS/ETCS on-board equipment
  [SELF]
  shall be capable,
  if
  [CONDITION]
  fitted with, to detect and record
  whether
  [CONDITION]
  the engine has been moved or not,
  during
  [TIME]
  a period of
  at least
  [WEAK]
  72 hours.
- kind: ordinary

##### 3.15.8.2 (Requirement Type)
When powered on again, the ERTMS/ETCS on-board equipment shall use, if available, the memorised information about cold movement in order to update the status of information stored by on-board equipment (see chapter 4 section 4.11 for details).
- WordTraceId: 250738
- atomic: true
- Legal Obligation: mandatory
- implement: true
- implementerEnhanced: When
  [CONDITION]
  powered on
  again
  [LOOP]
  , the
  ERTMS/ETCS on-board equipment
  [SELF]
  shall use,
  if
  [CONDITION]
  available, the memorised information about cold movement in order to update the status of information stored by
  on-board equipment
  [SELF]
  (see chapter 4 section 4.11 for details).
- kind: ordinary
- CrossRefLink -> 4.11

##### 3.15.8.3 (Requirement Type)
Note: information memorised by Cold Movement Detection function is considered as not available if:
- WordTraceId: 250982
- atomic: false
- Legal Obligation: not applicable
- implement: false
- implementerEnhanced: Note: information memorised by Cold Movement Detection function is considered as not available
  if
  [CONDITION]
  :
- kind: Note

###### 3.15.8.3.a (Requirement Type)
no Cold Movement Detection function is implemented in the ERTMS/ETCS on-board equipment, OR
- WordTraceId: 251081
- atomic: true
- Legal Obligation: unknown
- implement: false
- implementerEnhanced: no Cold Movement Detection function is implemented in the
  ERTMS/ETCS on-board equipment
  [SELF]
  , OR
- ListNumberText: a)
- kind: Note

###### 3.15.8.3.b (Requirement Type)
the Cold Movement Detection function has encountered a condition, during the No Power period, which prevents the use of the Cold Movement information (e.g. the battery ensuring the Cold Movement Detection function has run down during the No Power period).
- WordTraceId: 251173
- atomic: true
- Legal Obligation: unknown
- implement: false
- implementerEnhanced: the Cold Movement Detection function has encountered a condition,
  during
  [TIME]
  the No Power period, which prevents the use of the Cold Movement information (
  e.g.
  [WEAK]
  the battery ensuring the Cold Movement Detection function has run down
  during
  [TIME]
  the No Power period).
- ListNumberText: b)
- kind: Note

#### 3.15.9 (Requirement Type)
Virtual Balise Cover
- WordTraceId: 251429
- atomic: false
- Legal Obligation: not applicable
- implement: false
- implementerEnhanced: Virtual
  Balise
  [EXTERNAL]
  Cover
- kind: Heading

##### 3.15.9.1 (Requirement Type)
It shall be possible to set and remove from balise a Virtual Balise Cover (VBC). A VBC is defined by:
- WordTraceId: 251450
- atomic: false
- Legal Obligation: mandatory
- implement: true
- implementerEnhanced: It shall be possible to set and remove from
  balise
  [EXTERNAL]
  a Virtual
  Balise
  [EXTERNAL]
  Cover (VBC). A VBC is defined by:
- kind: ordinary

###### 3.15.9.1.a (Requirement Type)
A marker corresponding to balises to be ignored by the on-board together with the area (country or region) in which the VBC is applicable. The VBC marker and the country/region identity form the unique VBC identity.
- WordTraceId: 251552
- atomic: false
- Legal Obligation: unknown
- implement: true
- implementerEnhanced: A marker corresponding to
  balises
  [EXTERNAL]
  to be ignored by the on-board together with the area (country or region) in which the VBC is applicable. The VBC marker and the country/region identity form the unique VBC identity.
- ListNumberText: a)
- kind: ordinary

###### 3.15.9.1.b (Requirement Type)
Its validity period.
- WordTraceId: 251768
- atomic: true
- Legal Obligation: unknown
- implement: true
- ListNumberText: b)
- kind: ordinary

##### 3.15.9.2 (Requirement Type)
During a start of mission, the driver shall have the opportunity to set a new VBC, or to remove an existing one.
- WordTraceId: 251789
- atomic: true
- Legal Obligation: mandatory
- implement: true
- implementerEnhanced: During
  [TIME]
  a start of mission, the
  driver
  [EXTERNAL]
  shall have the opportunity to set a new VBC, or to remove an existing one.
- kind: ordinary

##### 3.15.9.3 (Requirement Type)
As long as a VBC is stored on-board:
- WordTraceId: 251902
- atomic: true
- Legal Obligation: unknown
- implement: false
- implementerEnhanced: As long as
  [TIME]
  a VBC is stored on-board:
- kind: Heading

###### 3.15.9.3.a (Requirement Type)
The ERTMS/ETCS on-board equipment shall ignore any balise telegram that includes a VBC marker and a country/region identity that both match the VBC identity.
- WordTraceId: 251939
- atomic: true
- Legal Obligation: mandatory
- implement: true
- implementerEnhanced: The
  ERTMS/ETCS on-board equipment
  [SELF]
  shall ignore any balise telegram that includes a VBC marker and a country/region identity that both match the VBC identity.
- ListNumberText: a)
- kind: ordinary

###### 3.15.9.3.b (Requirement Type)
No reaction shall be applied if errors in the reading of the rest of such balise telegram occur.
- WordTraceId: 252097
- atomic: true
- Legal Obligation: mandatory
- implement: true
- implementerEnhanced: No reaction shall be applied
  if
  [CONDITION]
  errors in the reading of the rest of such balise telegram occur.
- ListNumberText: b)
- kind: ordinary

##### 3.15.9.4 (Requirement Type)
If the ERTMS/ETCS on-board equipment receives from balise or from driver a new VBC with the same VBC identity as an already stored VBC, the new VBC shall replace the previous one, including its validity period.
- WordTraceId: 252194
- atomic: true
- Legal Obligation: mandatory
- implement: true
- implementerEnhanced: If
  [CONDITION]
  the
  ERTMS/ETCS on-board equipment
  [SELF]
  receives from
  balise
  [EXTERNAL]
  or from
  driver
  [EXTERNAL]
  a new VBC with the same VBC identity as an already stored VBC, the new VBC shall replace the previous one, including its validity period.
- kind: ordinary

##### 3.15.9.5 (Requirement Type)
A VBC shall be retained on-board when the on-board equipment is switched off (i.e. enters No Power mode) and shall remain applicable when powered on again. It shall be deleted when:
- WordTraceId: 252405
- atomic: false
- Legal Obligation: mandatory
- implement: true
- implementerEnhanced: A VBC shall be retained on-board
  when
  [CONDITION]
  the
  on-board equipment
  [SELF]
  is switched off (i.e. enters No Power mode) and shall remain applicable
  when
  [CONDITION]
  powered on
  again
  [LOOP]
  . It shall be deleted
  when
  [CONDITION]
  :
- kind: ordinary

###### 3.15.9.5.a (Requirement Type)
it is ordered by trackside, or
- WordTraceId: 252587
- atomic: true
- Legal Obligation: mandatory (>= 1)
- implement: true
- implementerEnhanced: it is ordered by
  trackside
  [EXTERNAL]
  , or
- ListNumberText: a)
- kind: ordinary

###### 3.15.9.5.b (Requirement Type)
its validity period has elapsed, or
- WordTraceId: 252618
- atomic: true
- Legal Obligation: mandatory (>= 1)
- implement: true
- ListNumberText: b)
- kind: ordinary

###### 3.15.9.5.c (Requirement Type)
it is removed by the driver (during Start of Mission), or
- WordTraceId: 252654
- atomic: true
- Legal Obligation: mandatory (>= 1)
- implement: true
- implementerEnhanced: it is removed by the
  driver
  [EXTERNAL]
  (
  during
  [TIME]
  Start of Mission), or
- ListNumberText: c)
- kind: ordinary

###### 3.15.9.5.d (Requirement Type)
a mismatch is detected between the country/region identity read from a balise group and the country/region identity of the VBC. Note: this means that the reception of a consistent balise group message is a necessary condition for deleting a VBC due to mismatching country/region identities.
- WordTraceId: 252712
- atomic: false
- Legal Obligation: mandatory (>= 1)
- implement: true
- implementerEnhanced: a mismatch is detected between the country/region identity read from a
  balise group
  [EXTERNAL]
  and the country/region identity of the VBC. Note: this means that the reception of a consistent
  balise group
  [EXTERNAL]
  message is a necessary condition for deleting a VBC due to mismatching country/region identities.
- ListNumberText: d)
- kind: ordinary

#### 3.15.10 (Requirement Type)
Advance display of route related information
- WordTraceId: 253003
- atomic: false
- Legal Obligation: not applicable
- implement: false
- kind: Heading

##### 3.15.10.1 (Requirement Type)
The ERTMS/ETCS on-board equipment shall offer the possibility to display, only on driver request, an overview of the gradient profile (as received from trackside), of the MRSP, of the track conditions (except the tunnel stopping areas), of the indication location at MRSP speed (see 3.13.10.4.11) and of the first target at zero speed, if any (e.g. the EOA or the start location of a mode profile), with the remaining distances referred to the train front end position.
- WordTraceId: 253048
- atomic: true
- Legal Obligation: mandatory
- implement: true
- implementerEnhanced: The
  ERTMS/ETCS on-board equipment
  [SELF]
  shall offer the possibility to display, only on
  driver
  [EXTERNAL]
  request, an overview of the gradient profile (as received from
  trackside
  [EXTERNAL]
  ), of the MRSP, of the track conditions (except the tunnel stopping areas), of the indication location at MRSP speed (see 3.13.10.4.11) and of the first target at zero speed,
  if
  [CONDITION]
  any (
  e.g.
  [WEAK]
  the EOA or the start location of a mode profile), with the remaining distances referred to the train front end position.
- kind: ordinary
- CrossRefLink -> 3.13.10.4.11

##### 3.15.10.2 (Requirement Type)
With regards to the MRSP, the track conditions, the indication location at MRSP speed and the first target at zero speed, the remaining distances shall be computed taking into account the min safe, the estimated or the max safe train front end position depending on their respective supervision.
- WordTraceId: 253518
- atomic: true
- Legal Obligation: mandatory
- implement: true
- kind: ordinary

##### 3.15.10.3 (Requirement Type)
With regards to the gradient profile, the remaining distances shall be computed taking into account the estimated train front end position.
- WordTraceId: 253814
- atomic: true
- Legal Obligation: mandatory
- implement: true
- kind: ordinary

##### 3.15.10.4 (Requirement Type)
The overview of route related information shall be restricted to the elements contained within the movement authority and up to the first target at zero speed, if any.
- WordTraceId: 253954
- atomic: true
- Legal Obligation: mandatory
- implement: true
- implementerEnhanced: The overview of route related information shall be restricted to the elements contained within the movement authority and up to the first target at zero speed,
  if
  [CONDITION]
  any.
- kind: ordinary

### 3.16 (Requirement Type)
Data C
o
nsistency
- WordTraceId: 254122
- atomic: false
- Legal Obligation: not applicable
- PlainText: Data Consistency
- implement: false
- implementerEnhanced: Data Consistency
- kind: Heading

#### 3.16.1 (Requirement Type)
Criteria of consistency
- WordTraceId: 254139
- atomic: false
- Legal Obligation: not applicable
- implement: false
- kind: Heading

##### 3.16.1.1 (Requirement Type)
The on-board shall not consider a message transmitted from the trackside if any of the following criteria is not fulfilled.
- WordTraceId: 254163
- atomic: true
- Legal Obligation: not applicable
- implement: false
- implementerEnhanced: The on-board shall not consider a message transmitted from the
  trackside
  [EXTERNAL]
  if
  [CONDITION]
  any of the following criteria is not fulfilled.
- kind: Heading

###### 3.16.1.1.a (Requirement Type)
Correctness of the received message: the whole message shall be complete and respect the ETCS language; variables shall not have invalid values
- WordTraceId: 254287
- atomic: false
- Legal Obligation: mandatory
- implement: true
- ListNumberText: a)
- kind: ordinary

###### 3.16.1.1.b (Requirement Type)
The message shall be received in due time.
- WordTraceId: 254432
- atomic: true
- Legal Obligation: mandatory
- implement: true
- implementerEnhanced: The message shall be received in due
  time
  [TIME]
  .
- ListNumberText: b)
- kind: ordinary

###### 3.16.1.1.c (Requirement Type)
The message shall be received at the right expected location.
- WordTraceId: 254475
- atomic: true
- Legal Obligation: mandatory
- implement: true
- ListNumberText: c)
- kind: ordinary

##### 3.16.1.1[2] (Requirement Type)
as stated below.
- WordTraceId: 254537
- atomic: true
- Legal Obligation: unknown
- implement: true
- implementerEnhanced: as stated
  below
  [WEAK]
  .
- kind: ordinary

###### 3.16.1.1[2].1 (Requirement Type)
Note: a value of a variable is invalid when a spare value is used.
- WordTraceId: 254554
- atomic: false
- Legal Obligation: not applicable
- implement: false
- implementerEnhanced: Note: a value of a variable is invalid
  when
  [CONDITION]
  a spare value is used.
- ListNumberText: 3.16.1.1.1
- kind: Note

#### 3.16.2 (Requirement Type)
Balises
- WordTraceId: 254621
- atomic: false
- Legal Obligation: not applicable
- implement: false
- implementerEnhanced: Balises
  [EXTERNAL]
- kind: Heading

##### 3.16.2.1 (Requirement Type)
Definitions
- WordTraceId: 254629
- atomic: false
- Legal Obligation: not applicable
- implement: false
- kind: Heading

###### 3.16.2.1.1 (Requirement Type)
The information that is sent from a balise is called a balise telegram.
- WordTraceId: 254641
- atomic: true
- Legal Obligation: unknown
- implement: false
- implementerEnhanced: The information that is sent from a
  balise
  [EXTERNAL]
  is called a balise telegram.
- kind: Definition

###### 3.16.2.1.2 (Requirement Type)
The whole set of information (balise telegram or telegrams) coming from a balise group is called a balise group message.
- WordTraceId: 254713
- atomic: true
- Legal Obligation: unknown
- implement: false
- implementerEnhanced: The whole set of information (balise telegram or telegrams) coming from a
  balise group
  [EXTERNAL]
  is called a
  balise group
  [EXTERNAL]
  message.
- kind: Definition

###### 3.16.2.1.2.1 (Requirement Type)
Note: In case of a balise group containing a single balise, telegram and message coincide.
- WordTraceId: 254835
- atomic: false
- Legal Obligation: not applicable
- implement: false
- implementerEnhanced: Note:
  In case of
  [CONDITION]
  a
  balise group
  [EXTERNAL]
  containing a single
  balise
  [EXTERNAL]
  , telegram and message coincide.
- kind: Note

###### 3.16.2.1.3 (Requirement Type)
A balise within a balise group shall be regarded as missed if
- WordTraceId: 254926
- atomic: true
- Legal Obligation: mandatory
- implement: false
- implementerEnhanced: A
  balise
  [EXTERNAL]
  within a
  balise group
  [EXTERNAL]
  shall be regarded as missed
  if
  [CONDITION]
- kind: Definition

###### 3.16.2.1.3.a (Requirement Type)
No balise is found within the maximum distance between balises from the previous balise in the group.
- WordTraceId: 254989
- atomic: true
- Legal Obligation: unknown
- implement: false
- implementerEnhanced: No
  balise
  [EXTERNAL]
  is found within the maximum distance between
  balises
  [EXTERNAL]
  from the previous
  balise
  [EXTERNAL]
  in the group.
- ListNumberText: a)
- kind: Definition

###### 3.16.2.1.3[2] (Requirement Type)
or
- WordTraceId: 255092
- atomic: true
- Legal Obligation: unknown
- implement: true
- kind: ordinary

###### 3.16.2.1.3[2].b (Requirement Type)
A following balise within the group has been passed.
- WordTraceId: 255095
- atomic: true
- Legal Obligation: unknown
- implement: true
- implementerEnhanced: A following
  balise
  [EXTERNAL]
  within the group has been passed.
- ListNumberText: b)
- kind: ordinary

##### 3.16.2.2 (Requirement Type)
General
- WordTraceId: 255148
- atomic: false
- Legal Obligation: not applicable
- implement: false
- kind: Heading

###### 3.16.2.2.1 (Requirement Type)
If the on-board is not able to recognise whether a balise group is linked or unlinked (if none of the balises in the balise group can be read correctly), it shall consider it as unlinked.
- WordTraceId: 255156
- atomic: true
- Legal Obligation: mandatory
- implement: true
- implementerEnhanced: If
  [CONDITION]
  the on-board is not able to recognise
  whether
  [CONDITION]
  a
  balise group
  [EXTERNAL]
  is linked or unlinked (
  if
  [CONDITION]
  none of the
  balises
  [EXTERNAL]
  in the
  balise group
  [EXTERNAL]
  can be read correctly), it shall consider it as unlinked.
- kind: ordinary

###### 3.16.2.2.2 (Requirement Type)
Deleted
- WordTraceId: 255344
- atomic: false
- Legal Obligation: not applicable
- implement: false
- kind: Placeholder

##### 3.16.2.3 (Requirement Type)
Linking Consistency
- WordTraceId: 255353
- atomic: false
- Legal Obligation: not applicable
- implement: false
- kind: Heading

###### 3.16.2.3.1 (Requirement Type)
If linking information is used the on-board shall react according to the linking reaction information in the following cases:
- WordTraceId: 255373
- atomic: true
- Legal Obligation: not applicable
- implement: false
- implementerEnhanced: If
  [CONDITION]
  linking information is used
  [LINKED_PHRASE]
  the on-board shall react according to the linking reaction information in the following cases:
- kind: Heading
- KnownTermLink -> 3.4.4.2.1.1

###### 3.16.2.3.1.a (Requirement Type)
If the location reference of the expected balise group is found in rear of the expectation window
- WordTraceId: 255499
- atomic: true
- Legal Obligation: mandatory
- implement: true
- implementerEnhanced: If
  [CONDITION]
  the location reference of the expected
  balise group
  [EXTERNAL]
  is found in rear of the expectation window
- ListNumberText: a)
- kind: ordinary

###### 3.16.2.3.1.b (Requirement Type)
If the location reference of the expected balise group is not found inside the expectation window (i.e. the end of the expectation window has been reached without having found the expected balise group)
- WordTraceId: 255597
- atomic: true
- Legal Obligation: mandatory
- implement: true
- implementerEnhanced: If
  [CONDITION]
  the location reference of the expected
  balise group
  [EXTERNAL]
  is not found inside the expectation window (i.e. the end of the expectation window has been reached without having found the expected
  balise group
  [EXTERNAL]
  )
- ListNumberText: b)
- kind: ordinary

###### 3.16.2.3.1.c (Requirement Type)
If inside the expectation window of the expected balise group another announced balise group, expected later, is found.
- WordTraceId: 255800
- atomic: true
- Legal Obligation: mandatory
- implement: true
- implementerEnhanced: If
  [CONDITION]
  inside the expectation window of the expected
  balise group
  [EXTERNAL]
  another announced
  balise group
  [EXTERNAL]
  , expected later, is found.
- ListNumberText: c)
- kind: ordinary

###### 3.16.2.3.1.1 (Requirement Type)
The ERTMS/ETCS on-board equipment shall ignore (i.e. it will not consider as LRBG) a balise group found with its location reference outside its expectation window.
- WordTraceId: 255920
- atomic: true
- Legal Obligation: mandatory
- implement: true
- implementerEnhanced: The
  ERTMS/ETCS on-board equipment
  [SELF]
  shall ignore (i.e. it will not consider as
  LRBG
  [EXTERNAL]
  ) a
  balise group
  [EXTERNAL]
  found with its location reference outside its expectation window.
- kind: ordinary

###### 3.16.2.3.2 (Requirement Type)
The on-board shall reject the message from the expected group and trip the train if the balise group is passed in the unexpected direction.
- WordTraceId: 256084
- atomic: true
- Legal Obligation: mandatory
- implement: true
- implementerEnhanced: The on-board shall reject the message from the expected group and trip the train
  if
  [CONDITION]
  the
  balise group
  [EXTERNAL]
  is passed in the unexpected direction.
- kind: ordinary

###### 3.16.2.3.2.1 (Requirement Type)
Exception: When the expected balise group is referred in the linking information with a balise group with ID “unknown”, 3.4.4.4.2.1 shall apply.
- WordTraceId: 256224
- atomic: true
- Legal Obligation: mandatory
- implement: true
- implementerEnhanced: Exception:
  When
  [CONDITION]
  the expected
  balise group
  [EXTERNAL]
  is referred in the linking information with a
  balise group
  [EXTERNAL]
  with ID “unknown”, 3.4.4.4.2.1 shall apply.
- kind: ordinary
- CrossRefLink -> 3.4.4.4.2.1

###### 3.16.2.3.3 (Requirement Type)
If the location reference balise of the group is duplicated and the on-board is only able to correctly evaluate the duplicating one, the duplicating one shall be used as location reference instead.
- WordTraceId: 256369
- atomic: true
- Legal Obligation: mandatory
- implement: true
- implementerEnhanced: If
  [CONDITION]
  the location reference
  balise
  [EXTERNAL]
  of the group is duplicated and the on-board is only able to correctly evaluate the duplicating one, the duplicating one shall be used as location reference instead.
- kind: ordinary

###### 3.16.2.3.4 (Requirement Type)
If the balise duplicating the location reference balise is used as location reference for the group, and is found within the expectation window, no linking reaction shall be applied.
- WordTraceId: 256567
- atomic: true
- Legal Obligation: mandatory
- implement: true
- implementerEnhanced: If
  [CONDITION]
  the
  balise
  [EXTERNAL]
  duplicating the location reference
  balise
  [EXTERNAL]
  is used as location reference for the group, and is found within the expectation window, no linking reaction shall be applied.
- kind: ordinary

##### 3.16.2.4 (Requirement Type)
Balise Group Message Consistency
- WordTraceId: 256750
- atomic: false
- Legal Obligation: not applicable
- implement: false
- implementerEnhanced: Balise Group
  [EXTERNAL]
  Message Consistency
- kind: Heading

###### 3.16.2.4.1 (Requirement Type)
If linking information is used, the on-board shall reject the message from a linked balise group found in the expected location and react according to the linking reaction in the following cases:
- WordTraceId: 256783
- atomic: true
- Legal Obligation: mandatory
- implement: true
- implementerEnhanced: If
  [CONDITION]
  linking information is used
  [LINKED_PHRASE]
  , the on-board shall reject the message from a linked
  balise group
  [EXTERNAL]
  found in the expected location and react according to the linking reaction in the following cases:
- kind: ordinary
- KnownTermLink -> 3.4.4.2.1.1

###### 3.16.2.4.1.a (Requirement Type)
A balise is missed inside the group.
- WordTraceId: 256979
- atomic: true
- Legal Obligation: mandatory
- implement: true
- implementerEnhanced: A
  balise
  [EXTERNAL]
  is missed inside the group.
- ListNumberText: a)
- kind: ordinary

###### 3.16.2.4.1.b (Requirement Type)
A balise is detected but no telegram is decoded (e.g. wrong CRC,...).
- WordTraceId: 257016
- atomic: true
- Legal Obligation: mandatory
- implement: true
- implementerEnhanced: A
  balise
  [EXTERNAL]
  is detected but no telegram is decoded (
  e.g.
  [WEAK]
  wrong CRC,
  ...
  [WEAK]
  ).
- ListNumberText: b)
- kind: ordinary

###### 3.16.2.4.1.c (Requirement Type)
Variables in the balise group message have invalid values.
- WordTraceId: 257086
- atomic: true
- Legal Obligation: mandatory
- implement: true
- implementerEnhanced: Variables in the
  balise group
  [EXTERNAL]
  message have invalid values.
- ListNumberText: c)
- kind: ordinary

###### 3.16.2.4.1.d (Requirement Type)
Message counters do not match (see 3.16.2.4.7)
- WordTraceId: 257145
- atomic: true
- Legal Obligation: mandatory
- implement: true
- ListNumberText: d)
- kind: ordinary
- CrossRefLink -> 3.16.2.4.7

###### 3.16.2.4.2 (Requirement Type)
Exception: Concerning a) and b) above, the ERTMS/ETCS on-board equipment shall not reject the message and shall not apply the linking reaction if the balise not found, or not decoded, is duplicated within the balise group and the duplicating one is correctly read.
- WordTraceId: 257192
- atomic: false
- Legal Obligation: mandatory
- implement: true
- implementerEnhanced: Exception: Concerning a) and b)
  above
  [WEAK]
  , the
  ERTMS/ETCS on-board equipment
  [SELF]
  shall not reject the message and shall not apply the linking reaction
  if
  [CONDITION]
  the
  balise
  [EXTERNAL]
  not found, or not decoded, is duplicated within the
  balise group
  [EXTERNAL]
  and the duplicating one is correctly read.
- kind: ordinary

###### 3.16.2.4.3 (Requirement Type)
If linking information is used, the on-board shall reject the message from a balise group marked as linked but not included in the linking information. No reaction shall be applied, even if errors in the reading of the balise group occur.
- WordTraceId: 257457
- atomic: false
- Legal Obligation: mandatory
- implement: true
- implementerEnhanced: If
  [CONDITION]
  linking information is used
  [LINKED_PHRASE]
  , the on-board shall reject the message from a
  balise group
  [EXTERNAL]
  marked as linked but not included in the linking information. No reaction shall be applied,
  even
  if
  [CONDITION]
  [WEAK]
  errors in the reading of the
  balise group
  [EXTERNAL]
  occur.
- kind: ordinary
- KnownTermLink -> 3.4.4.2.1.1

###### 3.16.2.4.4 (Requirement Type)
If no linking information is used, the on-board shall reject the message from a balise group marked as linked and command application of the service brake in the following cases:
- WordTraceId: 257696
- atomic: true
- Legal Obligation: mandatory
- implement: true
- implementerEnhanced: If
  [CONDITION]
  no
  linking information is used
  [LINKED_PHRASE]
  , the on-board shall reject the message from a
  balise group
  [EXTERNAL]
  marked as linked and command application of the service brake in the following cases:
- kind: ordinary
- KnownTermLink -> 3.4.4.2.1.1

###### 3.16.2.4.4.a (Requirement Type)
A balise is missed inside the group.
- WordTraceId: 257875
- atomic: true
- Legal Obligation: mandatory
- implement: true
- implementerEnhanced: A
  balise
  [EXTERNAL]
  is missed inside the group.
- ListNumberText: a)
- kind: ordinary

###### 3.16.2.4.4.b (Requirement Type)
A balise is detected, but no telegram is decoded (e.g. wrong CRC).
- WordTraceId: 257912
- atomic: true
- Legal Obligation: mandatory
- implement: true
- implementerEnhanced: A
  balise
  [EXTERNAL]
  is detected, but no telegram is decoded (
  e.g.
  [WEAK]
  wrong CRC).
- ListNumberText: b)
- kind: ordinary

###### 3.16.2.4.4.c (Requirement Type)
Variables in the balise group message have invalid values.
- WordTraceId: 257979
- atomic: true
- Legal Obligation: mandatory
- implement: true
- implementerEnhanced: Variables in the
  balise group
  [EXTERNAL]
  message have invalid values.
- ListNumberText: c)
- kind: ordinary

###### 3.16.2.4.4.d (Requirement Type)
Message counters do not match (see 3.16.2.4.7)
- WordTraceId: 258038
- atomic: true
- Legal Obligation: mandatory
- implement: true
- ListNumberText: d)
- kind: ordinary
- CrossRefLink -> 3.16.2.4.7

###### 3.16.2.4.4.1 (Requirement Type)
Exceptions: Concerning a) and b) of clause 3.16.2.4.4, the ERTMS/ETCS on-board equipment:
- WordTraceId: 258085
- atomic: true
- Legal Obligation: mandatory
- implement: true
- implementerEnhanced: Exceptions: Concerning a) and b) of clause 3.16.2.4.4, the
  ERTMS/ETCS on-board equipment
  [SELF]
  :
- kind: ordinary
- CrossRefLink -> 3.16.2.4.4.a
- CrossRefLink -> 3.16.2.4.4.b

###### 3.16.2.4.4.1.a (Requirement Type)
shall not reject the message and shall not command application of the service brake if the balise not found, or not decoded, is duplicated within the balise group, the duplicating one is correctly read and contains:
- WordTraceId: 258176
- atomic: false
- Legal Obligation: mandatory
- implement: true
- implementerEnhanced: shall not reject the message and shall not command application of the service brake
  if
  [CONDITION]
  the
  balise
  [EXTERNAL]
  not found, or not decoded, is duplicated within the
  balise group
  [EXTERNAL]
  , the duplicating one is correctly read and contains:
- ListNumberText: a)
- kind: ordinary

###### 3.16.2.4.4.1.a.*[1] (Requirement Type)
directional information while the orientation of the balise group can still be evaluated, or
- WordTraceId: 258392
- atomic: true
- Legal Obligation: mandatory (>= 1)
- implement: true
- implementerEnhanced: directional information
  while
  [TIME]
  the orientation of the
  balise group
  [EXTERNAL]
  can still be evaluated, or
- ListNumberText: ·
- kind: ordinary

###### 3.16.2.4.4.1.a.*[2] (Requirement Type)
only information valid for both directions, or
- WordTraceId: 258485
- atomic: true
- Legal Obligation: mandatory (>= 1)
- implement: true
- ListNumberText: ·
- kind: ordinary

###### 3.16.2.4.4.1.a.*[3] (Requirement Type)
neither directional information nor information valid for both directions, or
- WordTraceId: 258532
- atomic: true
- Legal Obligation: mandatory (>= 1)
- implement: true
- ListNumberText: ·
- kind: ordinary

###### 3.16.2.4.4.1.a.*[4] (Requirement Type)
only data to be used by applications outside ERTMS/ETCS, or
- WordTraceId: 258610
- atomic: true
- Legal Obligation: mandatory (>= 1)
- implement: true
- ListNumberText: ·
- kind: ordinary

###### 3.16.2.4.4.1.a.*[5] (Requirement Type)
only data to be used by applications outside ERTMS/ETCS together with other information valid for both directions.
- WordTraceId: 258670
- atomic: true
- Legal Obligation: mandatory (>= 1)
- implement: true
- ListNumberText: ·
- kind: ordinary

###### 3.16.2.4.4.1.b (Requirement Type)
shall not command application of the service brake if the telegram correctly read from another balise of the group contains the information “Inhibition of balise group message consistency reaction”.
- WordTraceId: 258785
- atomic: true
- Legal Obligation: mandatory
- implement: true
- implementerEnhanced: shall not command application of the service brake
  if
  [CONDITION]
  the telegram correctly read from another
  balise
  [EXTERNAL]
  of the group contains the information “Inhibition of
  balise group
  [EXTERNAL]
  message consistency reaction”.
- ListNumberText: b)
- kind: ordinary

###### 3.16.2.4.4.2 (Requirement Type)
Concerning clause 3.16.2.4.4, if the service brake is applied, the location based information stored on-board shall be shortened to the current position when the train has reached standstill. Refer to appendix A.3.4 for the exhaustive list of information, which shall be shortened.
- WordTraceId: 258984
- atomic: false
- Legal Obligation: mandatory
- implement: true
- implementerEnhanced: Concerning clause 3.16.2.4.4,
  if
  [CONDITION]
  the service brake is applied, the location based information stored on-board shall be shortened to the current position
  when
  [CONDITION]
  the train has reached standstill. Refer to appendix A.3.4 for the exhaustive list of information, which shall be shortened.
- kind: ordinary
- CrossRefLink -> 3.16.2.4.4
- CrossRefLink -> A.3.4

###### 3.16.2.4.4.3 (Requirement Type)
Concerning clause 3.16.2.4.4, if the service brake is applied, the driver shall be informed that this is due to a balise group message consistency problem.
- WordTraceId: 259266
- atomic: true
- Legal Obligation: mandatory
- implement: true
- implementerEnhanced: Concerning clause 3.16.2.4.4,
  if
  [CONDITION]
  the service brake is applied, the
  driver
  [EXTERNAL]
  shall be informed that this is due to a
  balise group
  [EXTERNAL]
  message consistency problem.
- kind: ordinary
- CrossRefLink -> 3.16.2.4.4

###### 3.16.2.4.5 (Requirement Type)
A message counter shall be attached to each balise telegram indicating which balise group message the telegram fits to.
- WordTraceId: 259422
- atomic: true
- Legal Obligation: mandatory
- implement: true
- implementerEnhanced: A message counter shall be attached to each balise telegram indicating which
  balise group
  [EXTERNAL]
  message the telegram fits to.
- kind: ordinary

###### 3.16.2.4.6 (Requirement Type)
Instead of a message counter corresponding to a given balise group message, it shall be possible to identify a telegram as always fitting all possible messages of the group.
- WordTraceId: 259542
- atomic: true
- Legal Obligation: mandatory
- implement: true
- implementerEnhanced: Instead of a message counter corresponding to a given
  balise group
  [EXTERNAL]
  message, it shall be possible to identify a telegram as always fitting all possible messages of the group.
- kind: ordinary

###### 3.16.2.4.6.1 (Requirement Type)
It shall also be possible to identify a telegram as never fitting any message of the group.
- WordTraceId: 259716
- atomic: true
- Legal Obligation: mandatory
- implement: true
- kind: ordinary

###### 3.16.2.4.7 (Requirement Type)
Comparing message counters of the received telegrams of a balise group message, excluding the ones complying with 3.16.2.4.6, if their values are not all identical, or at least one of them complies with 3.16.2.4.6.1, this shall be considered as a message consistency error.
The balise group can, however, be used for location information.
- WordTraceId: 259808
- atomic: false
- Legal Obligation: mandatory
- implement: true
- implementerEnhanced: Comparing message counters of the received telegrams of a
  balise group
  [EXTERNAL]
  message, excluding the ones complying with 3.16.2.4.6,
  if
  [CONDITION]
  their values are not all identical, or
  at least
  [WEAK]
  one of them complies with 3.16.2.4.6.1, this shall be considered as a message consistency error. The
  balise group
  [EXTERNAL]
  can, however, be used for location information.
- kind: ordinary
- CrossRefLink -> 3.16.2.4.6
- CrossRefLink -> 3.16.2.4.6.1

###### 3.16.2.4.7.1 (Requirement Type)
In case of single balise group, if the message counter of the received telegram complies with 3.16.2.4.6.1, this shall also be considered as a message consistency error.
- WordTraceId: 260147
- atomic: true
- Legal Obligation: mandatory
- implement: true
- implementerEnhanced: In case of
  [CONDITION]
  single
  balise group
  [EXTERNAL]
  ,
  if
  [CONDITION]
  the message counter of the received telegram complies with 3.16.2.4.6.1, this shall also be considered as a message consistency error.
- kind: ordinary
- CrossRefLink -> 3.16.2.4.6.1

###### 3.16.2.4.8 (Requirement Type)
It shall be possible to indicate failures in the system underlying the balise/loop/RIU (e.g. the Lineside Electronic Unit, LEU) by sending a balise telegram, a loop message or a RIU message including the information "default balise/loop/RIU information".
- WordTraceId: 260317
- atomic: true
- Legal Obligation: mandatory
- implement: true
- implementerEnhanced: It shall be possible to indicate failures in the system underlying the
  balise
  [EXTERNAL]
  /
  loop
  [EXTERNAL]
  /
  RIU
  [EXTERNAL]
  (
  e.g.
  [WEAK]
  the
  Lineside Electronic Unit
  [EXTERNAL]
  ,
  LEU
  [EXTERNAL]
  ) by sending a balise telegram, a
  loop
  [EXTERNAL]
  message or a
  RIU
  [EXTERNAL]
  message including the information "default
  balise
  [EXTERNAL]
  /
  loop
  [EXTERNAL]
  /
  RIU
  [EXTERNAL]
  information".
- kind: ordinary

###### 3.16.2.4.8.1 (Requirement Type)
If one (and only one) out of a pair of duplicated balise telegrams received by the on-board includes the information “default balise information”, the on-board shall ignore any other information included in this telegram and shall consider information from the telegram not containing “default balise information".
- WordTraceId: 260572
- atomic: false
- Legal Obligation: mandatory
- implement: true
- implementerEnhanced: If
  [CONDITION]
  one (and only one) out of a pair of duplicated balise telegrams received by the on-board includes the information “
  default
  balise
  [EXTERNAL]
  information
  [LINKED_PHRASE]
  ”, the on-board shall ignore any other information included in this telegram and shall consider information from the telegram not containing “
  default
  balise
  [EXTERNAL]
  information
  [LINKED_PHRASE]
  ".
- kind: ordinary
- KnownTermLink -> 3.16.2.4.8

###### 3.16.2.4.8.2 (Requirement Type)
When duplicated balises are both found and decoded correctly, and both, or none of them, contain "default balise information", the ERTMS/ETCS on-board equipment shall compose the message using the telegram from the last received balise out of the pair.
- WordTraceId: 260887
- atomic: true
- Legal Obligation: mandatory
- implement: true
- implementerEnhanced: When
  [CONDITION]
  duplicated
  balises
  [EXTERNAL]
  are both found and decoded correctly, and both, or none of them, contain "
  default
  balise
  [EXTERNAL]
  information
  [LINKED_PHRASE]
  ", the
  ERTMS/ETCS on-board equipment
  [SELF]
  shall compose the message using the telegram from the last received
  balise
  [EXTERNAL]
  out of the pair.
- kind: ordinary
- KnownTermLink -> 3.16.2.4.8

###### 3.16.2.4.9 (Requirement Type)
If a message has been received containing the information "default balise information", the driver shall be informed.
- WordTraceId: 261140
- atomic: true
- Legal Obligation: mandatory
- implement: true
- implementerEnhanced: If
  [CONDITION]
  a message has been received containing the information "
  default
  balise
  [EXTERNAL]
  information
  [LINKED_PHRASE]
  ", the
  driver
  [EXTERNAL]
  shall be informed.
- kind: ordinary
- KnownTermLink -> 3.16.2.4.8

##### 3.16.2.5 (Requirement Type)
Unlinked Balise Group Message Consistency
- WordTraceId: 261258
- atomic: false
- Legal Obligation: not applicable
- implement: false
- implementerEnhanced: Unlinked
  Balise Group
  [EXTERNAL]
  Message Consistency
- kind: Heading

###### 3.16.2.5.1 (Requirement Type)
An on-board equipment shall reject the message received from a balise group marked as unlinked and command application of the service brake in the following cases:
- WordTraceId: 261300
- atomic: true
- Legal Obligation: mandatory
- implement: true
- implementerEnhanced: An
  on-board equipment
  [SELF]
  shall reject the message received from a
  balise group
  [EXTERNAL]
  marked as unlinked and command application of the service brake in the following cases:
- kind: ordinary

###### 3.16.2.5.1.a (Requirement Type)
A balise is missed inside the unlinked balise group.
- WordTraceId: 261464
- atomic: true
- Legal Obligation: mandatory
- implement: true
- implementerEnhanced: A
  balise
  [EXTERNAL]
  is missed inside the unlinked
  balise group
  [EXTERNAL]
  .
- ListNumberText: a)
- kind: ordinary

###### 3.16.2.5.1.b (Requirement Type)
A balise is detected, but no telegram is decoded (e.g. wrong CRC).
- WordTraceId: 261517
- atomic: true
- Legal Obligation: mandatory
- implement: true
- implementerEnhanced: A
  balise
  [EXTERNAL]
  is detected, but no telegram is decoded (
  e.g.
  [WEAK]
  wrong CRC).
- ListNumberText: b)
- kind: ordinary

###### 3.16.2.5.1.c (Requirement Type)
Variables in the balise group message have invalid values.
- WordTraceId: 261584
- atomic: true
- Legal Obligation: mandatory
- implement: true
- implementerEnhanced: Variables in the
  balise group
  [EXTERNAL]
  message have invalid values.
- ListNumberText: c)
- kind: ordinary

###### 3.16.2.5.1.d (Requirement Type)
Message counters do not match (see 3.16.2.4.7)
- WordTraceId: 261643
- atomic: true
- Legal Obligation: mandatory
- implement: true
- ListNumberText: d)
- kind: ordinary
- CrossRefLink -> 3.16.2.4.7

###### 3.16.2.5.1.1 (Requirement Type)
Exceptions: Concerning a) and b) of clause 3.16.2.5.1, the ERTMS/ETCS on-board equipment:
- WordTraceId: 261690
- atomic: true
- Legal Obligation: mandatory
- implement: true
- implementerEnhanced: Exceptions: Concerning a) and b) of clause 3.16.2.5.1, the
  ERTMS/ETCS on-board equipment
  [SELF]
  :
- kind: ordinary
- CrossRefLink -> 3.16.2.5.1.a
- CrossRefLink -> 3.16.2.5.1.b

###### 3.16.2.5.1.1.a (Requirement Type)
shall not reject the message and shall not command application of the service brake if the balise not found, or not decoded, is duplicated within the balise group, the duplicating one is correctly read and contains:
- WordTraceId: 261780
- atomic: false
- Legal Obligation: mandatory
- implement: true
- implementerEnhanced: shall not reject the message and shall not command application of the service brake
  if
  [CONDITION]
  the
  balise
  [EXTERNAL]
  not found, or not decoded, is duplicated within the
  balise group
  [EXTERNAL]
  , the duplicating one is correctly read and contains:
- ListNumberText: a)
- kind: ordinary

###### 3.16.2.5.1.1.a.*[1] (Requirement Type)
directional information while the orientation of the balise group can still be evaluated, or
- WordTraceId: 261997
- atomic: true
- Legal Obligation: mandatory (>= 1)
- implement: true
- implementerEnhanced: directional information
  while
  [TIME]
  the orientation of the
  balise group
  [EXTERNAL]
  can still be evaluated, or
- ListNumberText: ·
- kind: ordinary

###### 3.16.2.5.1.1.a.*[2] (Requirement Type)
only information valid for both directions, or
- WordTraceId: 262090
- atomic: true
- Legal Obligation: mandatory (>= 1)
- implement: true
- ListNumberText: ·
- kind: ordinary

###### 3.16.2.5.1.1.a.*[3] (Requirement Type)
neither directional information nor information valid for both directions, or
- WordTraceId: 262137
- atomic: true
- Legal Obligation: mandatory (>= 1)
- implement: true
- ListNumberText: ·
- kind: ordinary

###### 3.16.2.5.1.1.a.*[4] (Requirement Type)
only data to be used by applications outside ERTMS/ETCS, or
- WordTraceId: 262215
- atomic: true
- Legal Obligation: mandatory (>= 1)
- implement: true
- ListNumberText: ·
- kind: ordinary

###### 3.16.2.5.1.1.a.*[5] (Requirement Type)
only data to be used by applications outside ERTMS/ETCS together with other information valid for both directions.
- WordTraceId: 262275
- atomic: true
- Legal Obligation: mandatory (>= 1)
- implement: true
- ListNumberText: ·
- kind: ordinary

###### 3.16.2.5.1.1.b (Requirement Type)
shall not command application of the service brake if the telegram correctly read from another balise of the group contains the information “Inhibition of balise group message consistency reaction”.
- WordTraceId: 262390
- atomic: true
- Legal Obligation: mandatory
- implement: true
- implementerEnhanced: shall not command application of the service brake
  if
  [CONDITION]
  the telegram correctly read from another
  balise
  [EXTERNAL]
  of the group contains the information “
  Inhibition of
  balise group
  [EXTERNAL]
  message consistency reaction
  [LINKED_PHRASE]
  ”.
- ListNumberText: b)
- kind: ordinary
- KnownTermLink -> 3.16.2.4.4.1.b

###### 3.16.2.5.2 (Requirement Type)
Concerning clause 3.16.2.5.1, if the service brake is applied, the location based information stored on-board shall be shortened to the current position when the train has reached standstill. Refer to appendix A.3.4 for the exhaustive list of information, which shall be shortened.
- WordTraceId: 262589
- atomic: false
- Legal Obligation: mandatory
- implement: true
- implementerEnhanced: Concerning clause 3.16.2.5.1,
  if
  [CONDITION]
  the service brake is applied, the location based information stored on-board shall be shortened to the current position
  when
  [CONDITION]
  the train has reached standstill. Refer to appendix A.3.4 for the exhaustive list of information, which shall be shortened.
- kind: ordinary
- CrossRefLink -> 3.16.2.5.1
- CrossRefLink -> A.3.4

###### 3.16.2.5.3 (Requirement Type)
Concerning clause 3.16.2.5.1, if the service brake is applied, the driver shall be informed that this is due to a balise group message consistency problem.
- WordTraceId: 262872
- atomic: true
- Legal Obligation: mandatory
- implement: true
- implementerEnhanced: Concerning clause 3.16.2.5.1,
  if
  [CONDITION]
  the service brake is applied, the
  driver
  [EXTERNAL]
  shall be informed that this is due to a
  balise group
  [EXTERNAL]
  message consistency problem.
- kind: ordinary
- CrossRefLink -> 3.16.2.5.1

##### 3.16.2.6 (Requirement Type)
Linking Reactions
- WordTraceId: 263028
- atomic: false
- Legal Obligation: not applicable
- implement: false
- kind: Heading

###### 3.16.2.6.1 (Requirement Type)
When the linking reaction leads to train trip or a service brake application, the driver shall be informed that the intervention is due to data consistency problem with the expected balise group.
- WordTraceId: 263046
- atomic: true
- Legal Obligation: mandatory
- implement: true
- implementerEnhanced: When
  [CONDITION]
  the linking reaction leads to train trip or a service brake application, the
  driver
  [EXTERNAL]
  shall be informed that the intervention is due to data consistency problem with the expected
  balise group
  [EXTERNAL]
  .
- kind: ordinary

###### 3.16.2.6.2 (Requirement Type)
If the service brake is initiated due to the linking reaction, the location based information stored on-board shall be shortened to the current position when the train has reached standstill. Refer to appendix A.3.4 for the exhaustive list of information, which shall be shortened.
- WordTraceId: 263242
- atomic: false
- Legal Obligation: mandatory
- implement: true
- implementerEnhanced: If
  [CONDITION]
  the service brake is initiated due to the linking reaction, the location based information stored on-board shall be shortened to the current position
  when
  [CONDITION]
  the train has reached standstill. Refer to appendix A.3.4 for the exhaustive list of information, which shall be shortened.
- kind: ordinary
- CrossRefLink -> A.3.4

##### 3.16.2.7 (Requirement Type)
RAMS related supervision functions
- WordTraceId: 263524
- atomic: false
- Legal Obligation: not applicable
- implement: false
- kind: Heading

###### 3.16.2.7.1 (Requirement Type)
Mitigation of balise reception degradation
- WordTraceId: 263559
- atomic: false
- Legal Obligation: not applicable
- implement: false
- implementerEnhanced: Mitigation of
  balise
  [EXTERNAL]
  reception degradation
- kind: Heading

###### 3.16.2.7.1.1 (Requirement Type)
If 2 consecutive linked balise groups announced by linking are not detected and the end of the expectation window of the second balise group has been passed, the ERTMS/ETCS on-board shall command the service brake and the driver shall be informed. At standstill, the location based information stored on-board shall be shortened to the current position. Refer to appendix A.3.4 for the exhaustive list of information, which shall be shortened.
- WordTraceId: 263602
- atomic: false
- Legal Obligation: mandatory
- implement: true
- implementerEnhanced: If
  [CONDITION]
  2 consecutive linked
  balise groups
  [EXTERNAL]
  announced by linking are not detected and the end of the expectation window of the second
  balise group
  [EXTERNAL]
  has been passed, the
  ERTMS/ETCS on-board
  [SELF]
  shall command the service brake and the
  driver
  [EXTERNAL]
  shall be informed. At standstill, the location based information stored on-board shall be shortened to the current position. Refer to appendix A.3.4 for the exhaustive list of information, which shall be shortened.
- kind: ordinary
- CrossRefLink -> A.3.4

###### 3.16.2.7.2 (Requirement Type)
Mitigation of balise cross-talk while expecting repositioning information
- WordTraceId: 264046
- atomic: false
- Legal Obligation: not applicable
- implement: false
- implementerEnhanced: Mitigation of
  balise
  [EXTERNAL]
  cross-talk
  while
  [TIME]
  expecting repositioning information
- kind: Heading

###### 3.16.2.7.2.1 (Requirement Type)
If repositioning is announced and the expected repositioning balise group has been found, the ERTMS/ETCS on-board equipment shall keep looking for a balise group that satisfies the same criteria as this previously expected and already found repositioning balise group, until one of the following events occurs:
- WordTraceId: 264120
- atomic: true
- Legal Obligation: mandatory
- implement: true
- implementerEnhanced: If
  [CONDITION]
  repositioning is announced and the expected repositioning
  balise group
  [EXTERNAL]
  has been found, the
  ERTMS/ETCS on-board equipment
  [SELF]
  shall keep looking for a
  balise group
  [EXTERNAL]
  that satisfies the same criteria as this previously expected and already found repositioning
  balise group
  [EXTERNAL]
  ,
  until
  [TIME]
  one of the following events occurs:
- kind: ordinary

###### 3.16.2.7.2.1.a (Requirement Type)
the on-board antenna leaves the expectation window of the repositioning balise group that was announced and already found
- WordTraceId: 264431
- atomic: true
- Legal Obligation: mandatory (== 1)
- implement: true
- implementerEnhanced: the on-board antenna leaves the expectation window of the repositioning
  balise group
  [EXTERNAL]
  that was announced and already found
- ListNumberText: a)
- kind: ordinary

###### 3.16.2.7.2.1.b (Requirement Type)
a linked balise group that has been announced with known identity is found.
- WordTraceId: 264553
- atomic: true
- Legal Obligation: mandatory (== 1)
- implement: true
- implementerEnhanced: a linked
  balise group
  [EXTERNAL]
  that has been announced with known identity is found.
- ListNumberText: b)
- kind: ordinary

###### 3.16.2.7.2.2 (Requirement Type)
If a second balise group is found that satisfies the same criteria as the previously expected and already found repositioning balise group, the ERTMS/ETCS on-board equipment shall command the service brake and the driver shall be informed. At standstill, the location based information stored on-board shall be shortened to the current position. Refer to appendix A.3.4 for the exhaustive list of information, which shall be shortened.
- WordTraceId: 264629
- atomic: false
- Legal Obligation: mandatory
- implement: true
- implementerEnhanced: If
  [CONDITION]
  a second
  balise group
  [EXTERNAL]
  is found that satisfies the same criteria as the previously expected and already found repositioning
  balise group
  [EXTERNAL]
  , the
  ERTMS/ETCS on-board equipment
  [SELF]
  shall command the service brake and the
  driver
  [EXTERNAL]
  shall be informed. At standstill, the location based information stored on-board shall be shortened to the current position. Refer to appendix A.3.4 for the exhaustive list of information, which shall be shortened.
- kind: ordinary
- CrossRefLink -> A.3.4

###### 3.16.2.7.2.3 (Requirement Type)
Note: this function is independent from linking function, i.e. the rules related to linking always apply. This means that once a repositioning balise group has been found and if this latter contains new linking information, the ERTMS/ETCS on-board equipment will start expecting the first balise group announced in this new linking information in parallel with the monitoring specified in 3.16.2.7.2.1.
- WordTraceId: 265065
- atomic: false
- Legal Obligation: not applicable
- implement: false
- implementerEnhanced: Note: this function is independent from linking function, i.e. the rules related to linking always apply. This means that once a repositioning
  balise group
  [EXTERNAL]
  has been found and
  if
  [CONDITION]
  this latter contains new linking information, the
  ERTMS/ETCS on-board equipment
  [SELF]
  will start expecting the first
  balise group
  [EXTERNAL]
  announced in this new linking information in parallel with the monitoring specified in 3.16.2.7.2.1.
- kind: Note
- CrossRefLink -> 3.16.2.7.2.1

#### 3.16.3 (Requirement Type)
Radio
- WordTraceId: 265468
- atomic: false
- Legal Obligation: not applicable
- implement: false
- kind: Heading

##### 3.16.3.1 (Requirement Type)
General issues
- WordTraceId: 265474
- atomic: false
- Legal Obligation: not applicable
- implement: false
- kind: Heading

###### 3.16.3.1.1 (Requirement Type)
A radio message is consistent when all checks have been completed successfully:
- WordTraceId: 265489
- atomic: true
- Legal Obligation: unknown
- implement: false
- implementerEnhanced: A radio message is consistent
  when
  [CONDITION]
  all checks have been completed successfully:
- kind: Heading

###### 3.16.3.1.1.a (Requirement Type)
Checks performed by Euroradio protocol have been passed (see Subset-037)
- WordTraceId: 265569
- atomic: true
- Legal Obligation: unknown
- implement: true
- ListNumberText: a)
- kind: ordinary

###### 3.16.3.1.1.b (Requirement Type)
Time stamps checks have been passed (see 3.16.3.3.3)
- WordTraceId: 265642
- atomic: true
- Legal Obligation: unknown
- implement: true
- implementerEnhanced: Time
  [TIME]
  stamps checks have been passed (see 3.16.3.3.3)
- ListNumberText: b)
- kind: ordinary
- CrossRefLink -> 3.16.3.3.3

###### 3.16.3.1.1.c (Requirement Type)
Variables in the messages do not have in-valid values.
- WordTraceId: 265695
- atomic: true
- Legal Obligation: unknown
- implement: true
- ListNumberText: c)
- kind: ordinary

###### 3.16.3.1.1.1 (Requirement Type)
The on-board shall reject a message transmitted from the trackside if the message is not consistent.
- WordTraceId: 265750
- atomic: true
- Legal Obligation: mandatory
- implement: true
- implementerEnhanced: The on-board shall reject a message transmitted from the
  trackside
  [EXTERNAL]
  if
  [CONDITION]
  the message is not consistent.
- kind: ordinary

###### 3.16.3.1.1.2 (Requirement Type)
The on-board shall inform the trackside if a not consistent message is received.
- WordTraceId: 265851
- atomic: true
- Legal Obligation: mandatory
- implement: true
- implementerEnhanced: The on-board shall inform the
  trackside
  [EXTERNAL]
  if
  [CONDITION]
  a not consistent message is received.
- kind: ordinary

###### 3.16.3.1.2 (Requirement Type)
Emergency messages shall be transmitted either as high priority data or as normal priority data.
- WordTraceId: 265932
- atomic: true
- Legal Obligation: mandatory
- implement: true
- kind: ordinary

###### 3.16.3.1.3 (Requirement Type)
Other messages shall be sent as normal priority data.
- WordTraceId: 266029
- atomic: true
- Legal Obligation: mandatory
- implement: true
- kind: ordinary

###### 3.16.3.1.3.1 (Requirement Type)
Messages shall only be accepted when received with the data priority for which they are specified.
- WordTraceId: 266083
- atomic: true
- Legal Obligation: mandatory
- implement: true
- implementerEnhanced: Messages shall only be accepted
  when
  [CONDITION]
  received with the data priority for which they are specified.
- kind: ordinary

###### 3.16.3.1.4 (Requirement Type)
The chapters 3.16.3.2 to 3.16.3.5 define data consistency principles and corresponding checks for data transmitted as normal priority data.
For high priority data, the checks shall not apply.
- WordTraceId: 266182
- atomic: false
- Legal Obligation: mandatory
- implement: true
- kind: ordinary
- CrossRefLink -> 3.16.3.2
- CrossRefLink -> 3.16.3.5

##### 3.16.3.2 (Requirement Type)
Time stamping
- WordTraceId: 266374
- atomic: false
- Legal Obligation: not applicable
- implement: false
- implementerEnhanced: Time
  [TIME]
  stamping
- kind: Heading

###### 3.16.3.2.1 (Requirement Type)
The trackside shall always transmit its information with reference to the train time.
- WordTraceId: 266388
- atomic: true
- Legal Obligation: mandatory
- implement: true
- implementerEnhanced: The
  trackside
  [EXTERNAL]
  shall always transmit its information with reference to the train
  time
  [TIME]
  .
- kind: ordinary

###### 3.16.3.2.2 (Requirement Type)
To time-stamp its messages, the trackside shall make a safe estimation of the on-board time, based on the time-stamp of the received messages and the internal processing times.
The estimation shall be made in such a way that the on-board time estimated by the trackside shall not be in advance of the real on-board time.
- WordTraceId: 266474
- atomic: false
- Legal Obligation: mandatory
- implement: true
- implementerEnhanced: To time-stamp its messages, the
  trackside
  [EXTERNAL]
  shall make a safe estimation of the on-board
  time
  [TIME]
  , based on the time-stamp of the received messages and the internal processing times. The estimation shall be made in such a way that the on-board
  time
  [TIME]
  estimated by the
  trackside
  [EXTERNAL]
  shall not be in advance of the real on-board
  time
  [TIME]
  .
- kind: ordinary

###### 3.16.3.2.3 (Requirement Type)
Wrap around of the onboard timer can occur during a communication session and shall have no impact on system behaviour.
- WordTraceId: 266795
- atomic: true
- Legal Obligation: mandatory
- implement: true
- implementerEnhanced: Wrap around of the onboard
  timer
  [TIME]
  can occur
  during
  [TIME]
  a communication session and shall have no impact on system behaviour.
- kind: ordinary

##### 3.16.3.3 (Requirement Type)
Supervision of Sequence
- WordTraceId: 266915
- atomic: false
- Legal Obligation: not applicable
- implement: false
- kind: Heading

###### 3.16.3.3.1 (Requirement Type)
The trackside shall time-stamp a message with a value corresponding to the time of sending.
- WordTraceId: 266939
- atomic: true
- Legal Obligation: mandatory
- implement: true
- implementerEnhanced: The
  trackside
  [EXTERNAL]
  shall time-stamp a message with a value corresponding to the
  time
  [TIME]
  of sending.
- kind: ordinary

###### 3.16.3.3.2 (Requirement Type)
There shall always be a time stamp increment between consecutive messages.
- WordTraceId: 267031
- atomic: true
- Legal Obligation: mandatory
- implement: true
- implementerEnhanced: There shall always be a
  time
  [TIME]
  stamp increment between consecutive messages.
- kind: ordinary

###### 3.16.3.3.3 (Requirement Type)
If the time stamp of the last received message is lower than or equal to the former one its content shall not be used.
- WordTraceId: 267106
- atomic: true
- Legal Obligation: mandatory
- implement: true
- implementerEnhanced: If
  [CONDITION]
  the
  time
  [TIME]
  stamp of the last received message is lower than or equal to the former one its content shall not be used.
- kind: ordinary

###### 3.16.3.3.3.1 (Requirement Type)
Only time stamps of messages received as normal priority data shall be used.
- WordTraceId: 267225
- atomic: true
- Legal Obligation: mandatory
- implement: true
- implementerEnhanced: Only
  time
  [TIME]
  stamps of messages received as normal priority data shall be used.
- kind: ordinary

###### 3.16.3.3.3.2 (Requirement Type)
Note: The supervision does not detect a lost message. This has to be assured by means of the “acknowledge” function.
- WordTraceId: 267302
- atomic: false
- Legal Obligation: not applicable
- implement: false
- kind: Note

###### 3.16.3.3.4 (Requirement Type)
If, at the initiation of the communication session, the time stamp is set to unknown the message shall be accepted.
- WordTraceId: 267419
- atomic: true
- Legal Obligation: mandatory
- implement: true
- implementerEnhanced: If
  [CONDITION]
  , at the initiation of the communication session, the
  time
  [TIME]
  stamp is set to unknown the message shall be accepted.
- kind: ordinary

###### 3.16.3.3.4[2] (Requirement Type)
- WordTraceId: 267535
- atomic: false
- Legal Obligation: not applicable
- implement: false
- kind: Placeholder

###### 3.16.3.3.4[2].[f]60 (Requirement Type)
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- WordTraceId: 267563
- atomic: false
- Legal Obligation: not applicable
- implement: false
- kind: Figure

###### 3.16.3.3.4[2].[f]60.C (Requirement Type)
Figure {Figure 60}: Supervision of sequence
- WordTraceId: 267563
- atomic: true
- Legal Obligation: unknown
- PlainText: Figure 60: Supervision of sequence
- implement: false
- implementerEnhanced: Figure 60: Supervision of sequence
- kind: Figure

##### 3.16.3.4 (Requirement Type)
Supervision of safe radio connection
- WordTraceId: 267623
- atomic: false
- Legal Obligation: not applicable
- implement: false
- kind: Heading

###### 3.16.3.4.1 (Requirement Type)
When the difference between the time stamp of the latest consistent received message and the current on-board time is greater than the T_NVCONTACT parameter (national value), the on-board shall apply the reaction as defined in the next section.
- WordTraceId: 267660
- atomic: true
- Legal Obligation: mandatory
- implement: true
- implementerEnhanced: When
  [CONDITION]
  the difference between the
  time
  [TIME]
  stamp of the latest consistent received message and the current on-board
  time
  [TIME]
  is greater than the T_NVCONTACT parameter (national value), the on-board shall apply the reaction as defined in the next section.
- kind: ordinary

###### 3.16.3.4.1.1 (Requirement Type)
After the on-board equipment has switched to L2 or 3 with no communication session established, the current onboard time shall be compared with the on-board time at the moment of the level transition (instead of the time stamp of the latest consistent received message) until a new consistent message has been received.
- WordTraceId: 267905
- atomic: true
- Legal Obligation: mandatory
- implement: true
- implementerEnhanced: After
  [TIME]
  the
  on-board equipment
  [SELF]
  has switched to L2 or 3 with no communication session established, the current onboard
  time
  [TIME]
  shall be compared with the on-board
  time
  [TIME]
  at the moment of the level transition (instead of the
  time
  [TIME]
  stamp of the latest consistent received message)
  until
  [TIME]
  a new consistent message has been received.
- kind: ordinary

###### 3.16.3.4.1.2 (Requirement Type)
When an RBC/RBC handover has been announced, the current onboard time shall be compared with the time stamp of the latest consistent message from the Handing over RBC until the train considers the Accepting RBC as the supervising one (refer to 3.15.1.3.5). From then on the current onboard time shall be compared with the time stamp of the latest received consistent message from the Accepting RBC.
- WordTraceId: 268225
- atomic: false
- Legal Obligation: mandatory
- implement: true
- implementerEnhanced: When
  [CONDITION]
  an
  RBC
  [EXTERNAL]
  /
  RBC
  [EXTERNAL]
  handover has been announced, the current onboard
  time
  [TIME]
  shall be compared with the
  time
  [TIME]
  stamp of the latest consistent message from the Handing over
  RBC
  [EXTERNAL]
  until
  [TIME]
  the train considers the Accepting
  RBC
  [EXTERNAL]
  as the supervising one (refer to 3.15.1.3.5). From then on the current onboard
  time
  [TIME]
  shall be compared with the
  time
  [TIME]
  stamp of the latest received consistent message from the Accepting
  RBC
  [EXTERNAL]
  .
- kind: ordinary
- CrossRefLink -> 3.15.1.3.5

###### 3.16.3.4.1.3 (Requirement Type)
After a train has passed an announced radio hole and until a new consistent message has been received, the current onboard time shall be compared with the on-board time when the train front end left the radio hole (instead of the time stamp of the latest consistent received message).
- WordTraceId: 268624
- atomic: true
- Legal Obligation: mandatory
- implement: true
- implementerEnhanced: After
  [TIME]
  a train has passed an announced radio hole and
  until
  [TIME]
  a new consistent message has been received, the current onboard
  time
  [TIME]
  shall be compared with the on-board
  time
  [TIME]
  when
  [CONDITION]
  the train front end left the radio hole (instead of the
  time
  [TIME]
  stamp of the latest consistent received message).
- kind: ordinary

###### 3.16.3.4.1.3[2] (Requirement Type)
- WordTraceId: 268909
- atomic: false
- Legal Obligation: not applicable
- implement: false
- kind: Placeholder

###### 3.16.3.4.1.3[2].[f]61 (Requirement Type)
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- WordTraceId: 268937
- atomic: false
- Legal Obligation: not applicable
- implement: false
- kind: Figure

###### 3.16.3.4.1.3[2].[f]61.C (Requirement Type)
Figure {Figure 61}: Supervision of the safe radio connection (Message received within the Window)
- WordTraceId: 268937
- atomic: true
- Legal Obligation: unknown
- PlainText: Figure 61: Supervision of the safe radio connection (Message received within the Window)
- implement: false
- kind: Figure

###### 3.16.3.4.1.3[3] (Requirement Type)
- WordTraceId: 269051
- atomic: false
- Legal Obligation: not applicable
- implement: false
- kind: Placeholder

###### 3.16.3.4.1.3[3].[f]62 (Requirement Type)
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- WordTraceId: 269078
- atomic: false
- Legal Obligation: not applicable
- implement: false
- kind: Figure

###### 3.16.3.4.1.3[3].[f]62.C (Requirement Type)
Figure {Figure 62}: Supervision of the safe radio connection (No message received within the Window)
- WordTraceId: 269078
- atomic: true
- Legal Obligation: unknown
- PlainText: Figure 62: Supervision of the safe radio connection (No message received within the Window)
- implement: false
- kind: Figure

###### 3.16.3.4.2 (Requirement Type)
It shall be possible to select one of the following reactions (National value) :
- WordTraceId: 269196
- atomic: true
- Legal Obligation: mandatory
- implement: true
- kind: ordinary

###### 3.16.3.4.2.a (Requirement Type)
Train trip
- WordTraceId: 269277
- atomic: true
- Legal Obligation: mandatory (== 1)
- implement: true
- ListNumberText: a)
- kind: ordinary

###### 3.16.3.4.2.b (Requirement Type)
Apply service brake
- WordTraceId: 269288
- atomic: true
- Legal Obligation: mandatory (== 1)
- implement: true
- ListNumberText: b)
- kind: ordinary

###### 3.16.3.4.2.c (Requirement Type)
No reaction
- WordTraceId: 269308
- atomic: true
- Legal Obligation: mandatory (== 1)
- implement: true
- ListNumberText: c)
- kind: ordinary

###### 3.16.3.4.3 (Requirement Type)
For all reactions, if no new consistent message has been received after an additional delay time (as defined in A3.1), the on-board shall release the safe radio connection and then set-up it again (maintaining the communication session).
- WordTraceId: 269320
- atomic: true
- Legal Obligation: mandatory
- implement: true
- implementerEnhanced: For all
  [LOOP]
  reactions,
  if
  [CONDITION]
  no new consistent message has been received
  after
  [TIME]
  an additional
  delay
  [TIME]
  time
  [TIME]
  (as defined in A3.1), the on-board shall release the safe radio connection and then set-up it
  again
  [LOOP]
  (maintaining the communication session).
- kind: ordinary
- CrossRefLink -> A.3.1

###### 3.16.3.4.4 (Requirement Type)
When the reaction leads to train trip or a service brake application, the driver shall be informed that no safe radio message has been received in due time.
- WordTraceId: 269558
- atomic: true
- Legal Obligation: mandatory
- implement: true
- implementerEnhanced: When
  [CONDITION]
  the reaction leads to train trip or a service brake application, the
  driver
  [EXTERNAL]
  shall be informed that no safe radio message has been received in due
  time
  [TIME]
  .
- kind: ordinary

###### 3.16.3.4.5 (Requirement Type)
If the service brake is initiated, the following reaction shall be taken;
- WordTraceId: 269715
- atomic: true
- Legal Obligation: not applicable
- implement: false
- implementerEnhanced: If
  [CONDITION]
  the service brake is initiated, the following reaction shall be taken;
- kind: Heading

###### 3.16.3.4.5.a (Requirement Type)
For brake command release conditions refer to section 3.14.1.7.
- WordTraceId: 269789
- atomic: true
- Legal Obligation: mandatory
- implement: true
- ListNumberText: a)
- kind: ordinary
- CrossRefLink -> 3.14.1.7

###### 3.16.3.4.5.b (Requirement Type)
If no new consistent message is received until the train reaches standstill, the location based information stored on-board shall be shortened to the current position. Refer to appendix A.3.4 for the exhaustive list of information, which shall be shortened.
- WordTraceId: 269853
- atomic: false
- Legal Obligation: mandatory
- implement: true
- implementerEnhanced: If
  [CONDITION]
  no new consistent message is received
  until
  [TIME]
  the train reaches standstill, the location based information stored on-board shall be shortened to the current position. Refer to appendix A.3.4 for the exhaustive list of information, which shall be shortened.
- ListNumberText: b)
- kind: ordinary
- CrossRefLink -> A.3.4

###### 3.16.3.4.6 (Requirement Type)
It shall be possible for the RBC to deactivate the supervision of T_NVCONTACT in some areas (e.g. radio hole).
- WordTraceId: 270111
- atomic: true
- Legal Obligation: mandatory
- implement: true
- implementerEnhanced: It shall be possible for the
  RBC
  [EXTERNAL]
  to deactivate the supervision of T_NVCONTACT in some areas (
  e.g.
  [WEAK]
  radio hole).
- kind: ordinary

###### 3.16.3.4.7 (Requirement Type)
To avoid the expiration of the on-board timer and if no new information is needed to be sent, the RBC shall send an empty message.
- WordTraceId: 270222
- atomic: true
- Legal Obligation: mandatory
- implement: true
- implementerEnhanced: To avoid the expiration of the on-board
  timer
  [TIME]
  and
  if
  [CONDITION]
  no new information is needed to be sent, the
  RBC
  [EXTERNAL]
  shall send an empty message.
- kind: ordinary

##### 3.16.3.5 (Requirement Type)
Message Acknowledgement
- WordTraceId: 270353
- atomic: false
- Legal Obligation: not applicable
- implement: false
- kind: Heading

###### 3.16.3.5.1 (Requirement Type)
As soon as a consistent message (see 3.16.3.1.1) including the request for acknowledgement is received, the on-board shall send an acknowledgement to the trackside.
- WordTraceId: 270377
- atomic: true
- Legal Obligation: mandatory
- implement: true
- implementerEnhanced: As soon as
  [WEAK]
  a consistent message (see 3.16.3.1.1) including the request for acknowledgement is received, the on-board shall send an acknowledgement to the
  trackside
  [EXTERNAL]
  .
- kind: ordinary
- CrossRefLink -> 3.16.3.1.1

###### 3.16.3.5.1.1 (Requirement Type)
Note: In order to ensure trackside that the on-board has correctly received transmitted information, the RBC may ask the on-board to acknowledge.
- WordTraceId: 270542
- atomic: false
- Legal Obligation: optional
- implement: false
- implementerEnhanced: Note: In order to ensure
  trackside
  [EXTERNAL]
  that the on-board has correctly received transmitted information, the
  RBC
  [EXTERNAL]
  may ask the on-board to acknowledge.
- kind: Note

###### 3.16.3.5.2 (Requirement Type)
Intentionally deleted
- WordTraceId: 270688
- atomic: false
- Legal Obligation: not applicable
- implement: false
- kind: Placeholder

###### 3.16.3.5.3 (Requirement Type)
The acknowledgement message shall refer to the identity of the concerned message sent by the RBC.
- WordTraceId: 270710
- atomic: true
- Legal Obligation: mandatory
- implement: true
- implementerEnhanced: The acknowledgement message shall refer to the identity of the concerned message sent by the
  RBC
  [EXTERNAL]
  .
- kind: ordinary

###### 3.16.3.5.4 (Requirement Type)
Intentionally deleted (moved to 3.5.5.1 e).
- WordTraceId: 270808
- atomic: true
- Legal Obligation: unknown
- implement: true
- kind: ordinary
- CrossRefLink -> 3.5.5.1.e

#### 3.16.4 (Requirement Type)
Error reporting to RBC
- WordTraceId: 270853
- atomic: false
- Legal Obligation: not applicable
- implement: false
- implementerEnhanced: Error reporting to
  RBC
  [EXTERNAL]
- kind: Heading

##### 3.16.4.1 (Requirement Type)
In level 2/3, if a radio communication session is established, errors shall be reported as soon as the availability of a safe radio connection permits.
- WordTraceId: 270876
- atomic: true
- Legal Obligation: mandatory
- implement: false
- implementerEnhanced: In level 2/3,
  if
  [CONDITION]
  a radio communication session is established, errors shall be reported
  as soon as
  [WEAK]
  the availability of a safe radio connection permits.
- kind: Definition

##### 3.16.4.2 (Requirement Type)
This refers to balise group errors and radio message errors regardless if there is an error reaction.
- WordTraceId: 271028
- atomic: true
- Legal Obligation: unknown
- implement: true
- implementerEnhanced: This refers to
  balise group
  [EXTERNAL]
  errors and radio message errors regardless
  if
  [CONDITION]
  there is an error reaction.
- kind: ordinary

##### 3.16.4.3 (Requirement Type)
If linking information is used on-board, no error reporting shall be done for balise groups marked as linked but not included in the linking information.
- WordTraceId: 271130
- atomic: true
- Legal Obligation: mandatory
- implement: true
- implementerEnhanced: If
  [CONDITION]
  linking information is used
  [LINKED_PHRASE]
  on-board, no error reporting shall be done for
  balise groups
  [EXTERNAL]
  marked as linked but not included in the linking information.
- kind: ordinary
- KnownTermLink -> 3.4.4.2.1.1

### 3.17 (Requirement Type)
System Version Management
- WordTraceId: 271284
- atomic: false
- Legal Obligation: not applicable
- implement: false
- kind: Heading

#### 3.17.1 (Requirement Type)
Introduction
- WordTraceId: 271311
- atomic: false
- Legal Obligation: not applicable
- implement: false
- kind: Heading

##### 3.17.1.1 (Requirement Type)
Definitions, high level principles and rules regarding the offline management of ERTMS/ETCS system version during the ERTMS/ETCS system life time are given in SUBSET-104.
- WordTraceId: 271324
- atomic: true
- Legal Obligation: unknown
- implement: false
- implementerEnhanced: Definitions, high level principles and rules regarding the offline management of ERTMS/ETCS system version
  during
  [TIME]
  the ERTMS/ETCS system life
  time
  [TIME]
  are given in SUBSET-104.
- kind: Definition

##### 3.17.1.2 (Requirement Type)
The objective of this section is to define requirements applicable to ERTMS/ETCS on-board equipment and to trackside constituents, when different versions of the ERTMS/ETCS system have been defined.
- WordTraceId: 271495
- atomic: true
- Legal Obligation: unknown
- implement: true
- implementerEnhanced: The objective of this section is to define requirements applicable to
  ERTMS/ETCS on-board equipment
  [SELF]
  and to
  trackside
  [EXTERNAL]
  constituents,
  when
  [CONDITION]
  different versions of the ERTMS/ETCS system have been defined.
- kind: ordinary

##### 3.17.1.3 (Requirement Type)
Intentionally deleted.
- WordTraceId: 271694
- atomic: false
- Legal Obligation: not applicable
- implement: false
- kind: Placeholder

#### 3.17.2 (Requirement Type)
Determination of the operated system version
- WordTraceId: 271717
- atomic: false
- Legal Obligation: not applicable
- implement: false
- kind: Heading

##### 3.17.2.1 (Requirement Type)
The on-board equipment shall be able to operate with (i.e. shall support) any of the ERTMS/ETCS system version numbers X included in the envelope of legally operated system versions, as defined in chapter 6.
- WordTraceId: 271762
- atomic: false
- Legal Obligation: mandatory
- implement: true
- implementerEnhanced: The
  on-board equipment
  [SELF]
  shall be able to operate with (i.e. shall support) any of the ERTMS/ETCS system version numbers X included in the envelope of legally operated system versions, as defined in chapter 6.
- kind: ordinary

##### 3.17.2.2 (Requirement Type)
The on-board equipment shall operate with only one system version at a time, i.e. it shall behave according to the whole set of requirements applicable to a system version (refer to chapter 6 in case the operated system version is older than the last one introduced in this release of the SRS).
- WordTraceId: 271970
- atomic: false
- Legal Obligation: mandatory
- implement: true
- implementerEnhanced: The
  on-board equipment
  [SELF]
  shall operate with only one system version at a
  time
  [TIME]
  , i.e. it shall behave according to the whole set of requirements applicable to a system version (refer to chapter 6
  in case
  [CONDITION]
  the operated system version is older than the last one introduced in this release of the SRS).
- kind: ordinary

##### 3.17.2.3 (Requirement Type)
The on-board equipment shall determine the operated system version, in relation to non-RBC trackside constituents, as the system version number X transmitted by any balise, loop or RIU, if this system version number X is higher than the currently operated one.
- WordTraceId: 272265
- atomic: true
- Legal Obligation: mandatory
- implement: true
- implementerEnhanced: The
  on-board equipment
  [SELF]
  shall determine the operated system version, in relation to non-RBC
  trackside
  [EXTERNAL]
  constituents, as the system version number X transmitted by any
  balise
  [EXTERNAL]
  ,
  loop
  [EXTERNAL]
  or
  RIU
  [EXTERNAL]
  ,
  if
  [CONDITION]
  this system version number X is higher than the currently operated one.
- kind: ordinary

##### 3.17.2.4 (Requirement Type)
It shall be possible from balise group to order the on-board equipment to operate a system version.
- WordTraceId: 272526
- atomic: true
- Legal Obligation: mandatory
- implement: true
- implementerEnhanced: It shall be possible from
  balise group
  [EXTERNAL]
  to order the
  on-board equipment
  [SELF]
  to operate a system version.
- kind: ordinary

##### 3.17.2.5 (Requirement Type)
On receiving the order to operate system version from balise group, the on-board equipment shall immediately operate the system version given in the order. After the order is executed, the requirement 3.17.2.3 shall be again applied for any further received balise telegram/loop message or any further contacted RIU.
- WordTraceId: 272626
- atomic: false
- Legal Obligation: mandatory
- implement: true
- implementerEnhanced: On receiving the order to operate system version from
  balise group
  [EXTERNAL]
  , the
  on-board equipment
  [SELF]
  shall
  immediately
  [WEAK]
  operate the system version given in the order.
  After
  [TIME]
  the order is executed, the requirement 3.17.2.3 shall be
  again
  [LOOP]
  applied for any further received balise telegram/
  loop
  [EXTERNAL]
  message or any further contacted
  RIU
  [EXTERNAL]
  .
- kind: ordinary
- CrossRefLink -> 3.17.2.3

###### 3.17.2.5.1 (Requirement Type)
Note: the system version order is to be used wherever it is necessary to enforce an operated system version number X lower than the currently operated one.
- WordTraceId: 272943
- atomic: false
- Legal Obligation: not applicable
- implement: false
- kind: Note

##### 3.17.2.6 (Requirement Type)
If a mismatch has been detected between the country or region identifier read from a balise/loop and the corresponding identifier(s) for which a set of national values is used onboard, the on-board equipment shall consider the system version number X transmitted by this balise/loop as the operated one and shall comply again with requirement 3.17.2.3.
- WordTraceId: 273099
- atomic: false
- Legal Obligation: mandatory
- implement: true
- implementerEnhanced: If
  [CONDITION]
  a mismatch has been detected between the country or region identifier read from a
  balise
  [EXTERNAL]
  /
  loop
  [EXTERNAL]
  and the corresponding identifier(s) for which a set of national values is used onboard, the
  on-board equipment
  [SELF]
  shall consider the system version number X transmitted by this
  balise
  [EXTERNAL]
  /
  loop
  [EXTERNAL]
  as the operated one and shall comply
  again
  [LOOP]
  with requirement 3.17.2.3.
- kind: ordinary
- CrossRefLink -> 3.17.2.3

##### 3.17.2.7 (Requirement Type)
If the on-board equipment does not support the system version number X transmitted by a non-RBC trackside constituent or the one specified in the balise group order, it shall consider the operated system version as unchanged.
- WordTraceId: 273452
- atomic: true
- Legal Obligation: mandatory
- implement: true
- implementerEnhanced: If
  [CONDITION]
  the
  on-board equipment
  [SELF]
  does not support the system version number X transmitted by a non-RBC
  trackside
  [EXTERNAL]
  constituent or the one specified in the
  balise group
  [EXTERNAL]
  order, it shall consider the operated system version as unchanged.
- kind: ordinary

##### 3.17.2.8 (Requirement Type)
In case of communication session established with an RBC, the system version of the RBC shall take precedence on the operated system version in relation to non-RBC constituents and on system version ordered from balise group; the operated system version shall be determined according to the following principles:
- WordTraceId: 273678
- atomic: false
- Legal Obligation: mandatory
- implement: true
- implementerEnhanced: In case of
  [CONDITION]
  communication session established with an
  RBC
  [EXTERNAL]
  , the system version of the
  RBC
  [EXTERNAL]
  shall take precedence on the operated system version in relation to non-RBC constituents and on system version ordered from
  balise group
  [EXTERNAL]
  ; the operated system version shall be determined according to the following principles:
- kind: ordinary

###### 3.17.2.8.a (Requirement Type)
if the on-board equipment is in level 0, NTC or 1 (e.g. entrance in level 2/3 area), the RBC system version shall be operated when the transition to level 2/3 is executed;
- WordTraceId: 273991
- atomic: true
- Legal Obligation: mandatory
- implement: true
- implementerEnhanced: if
  [CONDITION]
  the
  on-board equipment
  [SELF]
  is in level 0, NTC or 1 (
  e.g.
  [WEAK]
  entrance in level 2/3 area), the
  RBC
  [EXTERNAL]
  system version shall be operated
  when
  [CONDITION]
  the transition to level 2/3 is executed;
- ListNumberText: a)
- kind: ordinary

###### 3.17.2.8.b (Requirement Type)
if the on-board equipment is in level 2/3 (SoM procedure or order received from trackside), the RBC system version shall be operated immediately;
- WordTraceId: 274163
- atomic: true
- Legal Obligation: mandatory
- implement: true
- implementerEnhanced: if
  [CONDITION]
  the
  on-board equipment
  [SELF]
  is in level 2/3 (SoM procedure or order received from
  trackside
  [EXTERNAL]
  ), the
  RBC
  [EXTERNAL]
  system version shall be operated
  immediately
  [WEAK]
  ;
- ListNumberText: b)
- kind: ordinary

###### 3.17.2.8.c (Requirement Type)
in case of session established with an accepting RBC (RBC/RBC Handover), the accepting RBC system version shall be operated as soon as the engine has passed the RBC/RBC border location with its maximum safe front end;
- WordTraceId: 274309
- atomic: true
- Legal Obligation: mandatory
- implement: true
- implementerEnhanced: in case of
  [CONDITION]
  session established with an accepting
  RBC
  [EXTERNAL]
  (
  RBC
  [EXTERNAL]
  /
  RBC
  [EXTERNAL]
  Handover), the accepting
  RBC
  [EXTERNAL]
  system version shall be operated
  as soon as
  [WEAK]
  the engine has passed the
  RBC
  [EXTERNAL]
  /
  RBC
  [EXTERNAL]
  border location with its maximum safe front end;
- ListNumberText: c)
- kind: ordinary

###### 3.17.2.8.d (Requirement Type)
in case the on-board equipment switches from level 2/3 to another level (e.g. exit from a level 2/3 area), the system version control in relation to non-RBC constituents shall be again applied and the balise group orders shall be again considered;
- WordTraceId: 274527
- atomic: false
- Legal Obligation: mandatory
- implement: true
- implementerEnhanced: in case
  [CONDITION]
  the
  on-board equipment
  [SELF]
  switches from level 2/3 to another level (
  e.g.
  [WEAK]
  exit from a level 2/3 area), the system version control in relation to non-RBC constituents shall be
  again
  [LOOP]
  applied and the
  balise group
  [EXTERNAL]
  orders shall be
  again
  [LOOP]
  considered;
- ListNumberText: d)
- kind: ordinary

###### 3.17.2.8.e (Requirement Type)
in case the engine passes the RBC/RBC border location with its maximum safe front end and no session is established with the accepting RBC, the system version control in relation to non-RBC constituents shall be again applied and the balise group orders shall be again considered.
- WordTraceId: 274775
- atomic: false
- Legal Obligation: mandatory
- implement: true
- implementerEnhanced: in case
  [CONDITION]
  the engine passes the
  RBC
  [EXTERNAL]
  /
  RBC
  [EXTERNAL]
  border location with its maximum safe front end and no session is established with the accepting
  RBC
  [EXTERNAL]
  , the system version control in relation to non-RBC constituents shall be
  again
  [LOOP]
  applied and the
  balise group
  [EXTERNAL]
  orders shall be
  again
  [LOOP]
  considered.
- ListNumberText: e)
- kind: ordinary

##### 3.17.2.9 (Requirement Type)
The system version currently operated when the on-board equipment is switched off (i.e. enters No Power mode) shall be retained and re-used when powered on.
- WordTraceId: 275056
- atomic: true
- Legal Obligation: mandatory
- implement: true
- implementerEnhanced: The system version currently operated
  when
  [CONDITION]
  the
  on-board equipment
  [SELF]
  is switched off (i.e. enters No Power mode) shall be retained and
  re-used
  [AGAIN]
  when
  [CONDITION]
  powered on.
- kind: ordinary

###### 3.17.2.9.1 (Requirement Type)
If the on-board equipment loses the information (failure situation), the highest supported system version shall be used.
- WordTraceId: 275213
- atomic: true
- Legal Obligation: mandatory
- implement: true
- implementerEnhanced: If
  [CONDITION]
  the
  on-board equipment
  [SELF]
  loses the information (failure situation), the highest supported system version shall be used.
- kind: ordinary

#### 3.17.3 (Requirement Type)
Handling of trackside data in relation to system version
- WordTraceId: 275334
- atomic: false
- Legal Obligation: not applicable
- implement: false
- implementerEnhanced: Handling of
  trackside
  [EXTERNAL]
  data in relation to system version
- kind: Heading

##### 3.17.3.1 (Requirement Type)
Every telegram transmitted by a balise, and every message transmitted by Euroloop and Radio Infill Unit shall contain only the data related to one system version. It is not allowed for the balise, Euroloop and Radio Infill Unit to transmit data correspondent to several system versions.
- WordTraceId: 275391
- atomic: false
- Legal Obligation: mandatory
- implement: true
- implementerEnhanced: Every telegram transmitted by a
  balise
  [EXTERNAL]
  , and every message transmitted by
  Euroloop
  [EXTERNAL]
  and
  Radio Infill Unit
  [EXTERNAL]
  shall contain only the data related to one system version. It is not allowed for the
  balise
  [EXTERNAL]
  ,
  Euroloop
  [EXTERNAL]
  and
  Radio Infill Unit
  [EXTERNAL]
  to transmit data correspondent to several system versions.
- kind: ordinary

##### 3.17.3.2 (Requirement Type)
All messages transmitted by an RBC shall contain data only related to one system version.
- WordTraceId: 275678
- atomic: true
- Legal Obligation: mandatory
- implement: true
- implementerEnhanced: All messages transmitted by an
  RBC
  [EXTERNAL]
  shall contain data only related to one system version.
- kind: ordinary

##### 3.17.3.3 (Requirement Type)
The on-board equipment shall check the system version prior to any further checks (data consistency, ..), as they depend on the system version.
- WordTraceId: 275768
- atomic: true
- Legal Obligation: mandatory
- implement: true
- implementerEnhanced: The
  on-board equipment
  [SELF]
  shall check the system version prior to any further checks (data consistency, ..), as they depend on the system version.
- kind: ordinary

##### 3.17.3.4 (Requirement Type)
Intentionally deleted.
- WordTraceId: 275912
- atomic: false
- Legal Obligation: not applicable
- implement: false
- kind: Placeholder

###### 3.17.3.4.1 (Requirement Type)
Intentionally deleted.
- WordTraceId: 275935
- atomic: false
- Legal Obligation: not applicable
- implement: false
- kind: Placeholder

###### 3.17.3.4.2 (Requirement Type)
Intentionally deleted.
- WordTraceId: 275958
- atomic: false
- Legal Obligation: not applicable
- implement: false
- kind: Placeholder

##### 3.17.3.5 (Requirement Type)
The on-board equipment shall check the ERTMS/ETCS system version number X transmitted by any balise:
- WordTraceId: 275981
- atomic: true
- Legal Obligation: mandatory
- implement: true
- implementerEnhanced: The
  on-board equipment
  [SELF]
  shall check the ERTMS/ETCS system version number X transmitted by any
  balise
  [EXTERNAL]
  :
- kind: ordinary

###### 3.17.3.5.a (Requirement Type)
In all levels, if this system version number X equals to 0, the balise information shall be ignored.
- WordTraceId: 276082
- atomic: true
- Legal Obligation: mandatory
- implement: true
- implementerEnhanced: In all levels,
  if
  [CONDITION]
  this system version number X equals to 0, the
  balise
  [EXTERNAL]
  information shall be ignored.
- ListNumberText: a)
- kind: ordinary

###### 3.17.3.5.b (Requirement Type)
In all levels, if this system version number X is different from 0 and lower than the lowest system version number X supported by the on-board equipment, it shall be able to interpret the balise information, to the extent defined for each type of information (see chapter 6 for detailed requirements). If the on-board is not able to interpret the information, this shall be considered as a message consistency error.
- WordTraceId: 276183
- atomic: false
- Legal Obligation: mandatory
- implement: true
- implementerEnhanced: In all levels,
  if
  [CONDITION]
  this system version number X is different from 0 and lower than the lowest system version number X supported by the
  on-board equipment
  [SELF]
  , it shall be able to interpret the
  balise
  [EXTERNAL]
  information, to the extent defined
  for each
  [LOOP]
  type of information (see chapter 6 for detailed requirements).
  If
  [CONDITION]
  the on-board is not able to interpret the information, this shall be considered as a message consistency error.
- ListNumberText: b)
- kind: ordinary

###### 3.17.3.5.c (Requirement Type)
In all levels, if this system version number X is amongst its supported ones, the on-board equipment shall be able to interpret the balise information. See chapter 6 for detailed requirements.
- WordTraceId: 276600
- atomic: false
- Legal Obligation: mandatory
- implement: true
- implementerEnhanced: In all levels,
  if
  [CONDITION]
  this system version number X is amongst its supported ones, the
  on-board equipment
  [SELF]
  shall be able to interpret the
  balise
  [EXTERNAL]
  information. See chapter 6 for detailed requirements.
- ListNumberText: c)
- kind: ordinary

###### 3.17.3.5.d (Requirement Type)
In levels 1, 2 and 3, if this system version number X is greater than the highest version number X supported by the on-board equipment, the information from this balise shall be ignored, the train shall be tripped and an indication shall be given to the driver.
- WordTraceId: 276793
- atomic: false
- Legal Obligation: mandatory
- implement: true
- implementerEnhanced: In levels 1, 2 and 3,
  if
  [CONDITION]
  this system version number X is greater than the highest version number X supported by the
  on-board equipment
  [SELF]
  , the information from this
  balise
  [EXTERNAL]
  shall be ignored, the train shall be tripped and an indication shall be given to the
  driver
  [EXTERNAL]
  .
- ListNumberText: d)
- kind: ordinary

###### 3.17.3.5.e (Requirement Type)
In levels 0 and NTC, if this system version number X is greater than the highest version number X supported by the on-board equipment, the information from this balise shall be ignored and no reaction shall be applied.
- WordTraceId: 277055
- atomic: false
- Legal Obligation: mandatory
- implement: true
- implementerEnhanced: In levels 0 and NTC,
  if
  [CONDITION]
  this system version number X is greater than the highest version number X supported by the
  on-board equipment
  [SELF]
  , the information from this
  balise
  [EXTERNAL]
  shall be ignored and no reaction shall be applied.
- ListNumberText: e)
- kind: ordinary

##### 3.17.3.6 (Requirement Type)
In level 1 the on-board equipment shall check the ERTMS/ETCS system version number X transmitted by any Euroloop found:
- WordTraceId: 277274
- atomic: true
- Legal Obligation: mandatory
- implement: true
- implementerEnhanced: In level 1 the
  on-board equipment
  [SELF]
  shall check the ERTMS/ETCS system version number X transmitted by any
  Euroloop
  [EXTERNAL]
  found:
- kind: ordinary

###### 3.17.3.6.a (Requirement Type)
if this system version number X is lower than the lowest system version number X supported by the on-board equipment, it shall be able to interpret the loop information, to the extent defined for each type of information (see chapter 6 for detailed requirements). If the on-board is not able to interpret the information, this shall be considered as a message consistency error.
- WordTraceId: 277394
- atomic: false
- Legal Obligation: mandatory
- implement: true
- implementerEnhanced: if
  [CONDITION]
  this system version number X is lower than the lowest system version number X supported by the
  on-board equipment
  [SELF]
  , it shall be able to interpret the
  loop
  [EXTERNAL]
  information, to the extent defined
  for each
  [LOOP]
  type of information (see chapter 6 for detailed requirements).
  If
  [CONDITION]
  the on-board is not able to interpret the information, this shall be considered as a message consistency error.
- ListNumberText: a)
- kind: ordinary

###### 3.17.3.6.b (Requirement Type)
if this system version number X is amongst its supported ones, the on-board equipment shall be able to interpret the loop information. See chapter 6 for detailed requirements.
- WordTraceId: 277773
- atomic: false
- Legal Obligation: mandatory
- implement: true
- implementerEnhanced: if
  [CONDITION]
  this system version number X is amongst its supported ones, the
  on-board equipment
  [SELF]
  shall be able to interpret the
  loop
  [EXTERNAL]
  information. See chapter 6 for detailed requirements.
- ListNumberText: b)
- kind: ordinary

###### 3.17.3.6.c (Requirement Type)
If this system version number X is greater than the highest version number X supported by the on-board equipment, no reaction shall be applied and the information from this loop shall be ignored.
- WordTraceId: 277949
- atomic: false
- Legal Obligation: mandatory
- implement: true
- implementerEnhanced: If
  [CONDITION]
  this system version number X is greater than the highest version number X supported by the
  on-board equipment
  [SELF]
  , no reaction shall be applied and the information from this
  loop
  [EXTERNAL]
  shall be ignored.
- ListNumberText: c)
- kind: ordinary

##### 3.17.3.7 (Requirement Type)
The on-board equipment shall check the ERTMS/ETCS system version number X transmitted the first time any RBC is contacted (including RBC hand over) or any RIU is contacted. Refer to section 3.5.3.8 for details.
- WordTraceId: 278145
- atomic: false
- Legal Obligation: mandatory
- implement: true
- implementerEnhanced: The
  on-board equipment
  [SELF]
  shall check the ERTMS/ETCS system version number X transmitted the first
  time
  [TIME]
  any
  RBC
  [EXTERNAL]
  is contacted (including
  RBC
  [EXTERNAL]
  hand over) or any
  RIU
  [EXTERNAL]
  is contacted. Refer to section 3.5.3.8 for details.
- kind: ordinary
- CrossRefLink -> 3.5.3.8

##### 3.17.3.8 (Requirement Type)
Intentionally deleted.
- WordTraceId: 278356
- atomic: false
- Legal Obligation: not applicable
- implement: false
- kind: Placeholder

##### 3.17.3.9 (Requirement Type)
Intentionally deleted.
- WordTraceId: 278379
- atomic: false
- Legal Obligation: not applicable
- implement: false
- kind: Placeholder

##### 3.17.3.10 (Requirement Type)
Intentionally deleted.
- WordTraceId: 278402
- atomic: false
- Legal Obligation: not applicable
- implement: false
- kind: Placeholder

##### 3.17.3.11 (Requirement Type)
For trackside information only differing by Y with regards to the highest system version number X supported by on-board, the on-board equipment shall not consider the reception of unknown packet/message as a message data consistency error (i.e. use of spare value for NID_PACKET or NID_MESSAGE) and shall ignore the content of the unknown packet/message in the following cases:
- WordTraceId: 278425
- atomic: false
- Legal Obligation: mandatory
- implement: true
- implementerEnhanced: For
  trackside
  [EXTERNAL]
  information only differing by Y with regards to the highest system version number X supported by on-board, the
  on-board equipment
  [SELF]
  shall not consider the reception of unknown packet/message as a message data consistency error (i.e. use of spare value for NID_PACKET or NID_MESSAGE) and shall ignore the content of the unknown packet/message in the following cases:
- kind: ordinary

###### 3.17.3.11.a (Requirement Type)
unknown packet included in a balise telegram/loop message related to the higher system version;
- WordTraceId: 278803
- atomic: true
- Legal Obligation: mandatory
- implement: true
- implementerEnhanced: unknown packet included in a balise telegram/
  loop
  [EXTERNAL]
  message related to the higher system version;
- ListNumberText: a)
- kind: ordinary

###### 3.17.3.11.b (Requirement Type)
unknown radio message from an RBC or RIU operating with the higher system version;
- WordTraceId: 278899
- atomic: true
- Legal Obligation: mandatory
- implement: true
- implementerEnhanced: unknown radio message from an
  RBC
  [EXTERNAL]
  or
  RIU
  [EXTERNAL]
  operating with the higher system version;
- ListNumberText: b)
- kind: ordinary

###### 3.17.3.11.c (Requirement Type)
unknown packet from an RBC or RIU operating with the higher system version, included in a message in which one or more optional packet can be added according to the version operated by on-board.
- WordTraceId: 278982
- atomic: true
- Legal Obligation: mandatory
- implement: true
- implementerEnhanced: unknown packet from an
  RBC
  [EXTERNAL]
  or
  RIU
  [EXTERNAL]
  operating with the higher system version, included in a message in which one or more optional packet can be added according to the version operated by on-board.
- ListNumberText: c)
- kind: ordinary

##### 3.17.3.12 (Requirement Type)
Intentionally deleted.
- WordTraceId: 279177
- atomic: false
- Legal Obligation: not applicable
- implement: false
- kind: Placeholder

###### 3.17.3.12.1 (Requirement Type)
Intentionally deleted.
- WordTraceId: 279200
- atomic: false
- Legal Obligation: not applicable
- implement: false
- kind: Placeholder

##### 3.17.3.13 (Requirement Type)
Intentionally deleted.
- WordTraceId: 279223
- atomic: false
- Legal Obligation: not applicable
- implement: false
- kind: Placeholder

### 3.18 (Requirement Type)
System Data
- WordTraceId: 279246
- atomic: false
- Legal Obligation: not applicable
- implement: false
- kind: Heading

#### 3.18.1 (Requirement Type)
Fixed Values
- WordTraceId: 279258
- atomic: false
- Legal Obligation: not applicable
- implement: false
- kind: Heading

##### 3.18.1.1 (Requirement Type)
Note: Appendix to chapter 3 contains a list of Fixed values used as system parameters in the supervision. These parameters are system related and can easily be changed in later versions of the ERTMS/ETCS if required. These parameters are not defined as National data.
- WordTraceId: 279271
- atomic: false
- Legal Obligation: not applicable
- implement: false
- implementerEnhanced: Note: Appendix to chapter 3 contains a list of Fixed values used as system parameters in the supervision. These parameters are system related and can easily be changed in later versions of the ERTMS/ETCS
  if
  [CONDITION]
  required. These parameters are not defined as National data.
- kind: Note

#### 3.18.2 (Requirement Type)
National / Default Values
- WordTraceId: 279540
- atomic: false
- Legal Obligation: not applicable
- implement: false
- kind: Heading

##### 3.18.2.1 (Requirement Type)
Note: Appendix to chapter 3 contains list of National and Default Values.
- WordTraceId: 279566
- atomic: false
- Legal Obligation: not applicable
- implement: false
- kind: Note

##### 3.18.2.2 (Requirement Type)
Trains shall be supervised according to the National Values of the current infrastructure if they are available on-board.
- WordTraceId: 279641
- atomic: true
- Legal Obligation: mandatory
- implement: true
- implementerEnhanced: Trains shall be supervised according to the National Values of the current infrastructure
  if
  [CONDITION]
  they are available on-board.
- kind: ordinary

##### 3.18.2.3 (Requirement Type)
National Values are transmitted with the area(s) (country or region) in which they are applicable. They shall become applicable at a defined location, or shall be applicable immediately.
- WordTraceId: 279764
- atomic: false
- Legal Obligation: mandatory
- implement: true
- implementerEnhanced: National Values are transmitted with the area(s) (country or region) in which they are applicable. They shall become applicable at a defined location, or shall be applicable
  immediately
  [WEAK]
  .
- kind: ordinary

##### 3.18.2.4 (Requirement Type)
Evaluating a balise group message, the balise identity information referring to the country or region shall be used to ensure that correct National Values are used.
- WordTraceId: 279951
- atomic: true
- Legal Obligation: mandatory
- implement: true
- implementerEnhanced: Evaluating a
  balise group
  [EXTERNAL]
  message, the
  balise
  [EXTERNAL]
  identity information referring to the country or region shall be used to ensure that correct National Values are used.
- kind: ordinary

##### 3.18.2.5 (Requirement Type)
For each National Value, the corresponding Default Value shall be used as fall back value if:
- WordTraceId: 280116
- atomic: true
- Legal Obligation: mandatory
- implement: true
- implementerEnhanced: For each
  [LOOP]
  National Value, the corresponding Default Value shall be used as fall back value
  if
  [CONDITION]
  :
- kind: ordinary

###### 3.18.2.5.*[1] (Requirement Type)
the National Value is not available, or
- WordTraceId: 280210
- atomic: true
- Legal Obligation: mandatory (>= 1)
- PlainText: the National Value  is not available, or
- implement: true
- ListNumberText: ·
- kind: ordinary

###### 3.18.2.5.*[2] (Requirement Type)
a mismatch has been detected between the country or region identifier read from a balise group and the corresponding identifier(s) of the applicable set with which the National Value was received and stored.
- WordTraceId: 280252
- atomic: true
- Legal Obligation: mandatory (>= 1)
- implement: true
- implementerEnhanced: a mismatch has been detected between the country or region identifier read from a
  balise group
  [EXTERNAL]
  and the corresponding identifier(s) of the applicable set with which the National Value was received and stored.
- ListNumberText: ·
- kind: ordinary

##### 3.18.2.6 (Requirement Type)
Note: even though the National Values are always transmitted as a single set for a given system version, the content of a set depends on the system version, so that when a set of National Values is received or becomes applicable, or when passing a balise group, the on-board equipment may apply clause 3.18.2.5 for a subset of National Values
- WordTraceId: 280460
- atomic: false
- Legal Obligation: optional
- implement: false
- implementerEnhanced: Note: even though the National Values are always transmitted as a single set for a given system version, the content of a set depends on the system version, so that
  when
  [CONDITION]
  a set of National Values is received or becomes applicable, or
  when
  [CONDITION]
  passing a
  balise group
  [EXTERNAL]
  , the
  on-board equipment
  [SELF]
  may apply clause 3.18.2.5 for a subset of National Values
- kind: Note
- CrossRefLink -> 3.18.2.5

##### 3.18.2.7 (Requirement Type)
The National Values currently applicable when the on-board equipment is switched off (i.e. enters No Power mode) shall be retained and shall remain applicable when powered on.
- WordTraceId: 280803
- atomic: false
- Legal Obligation: mandatory
- implement: true
- implementerEnhanced: The National Values currently applicable
  when
  [CONDITION]
  the
  on-board equipment
  [SELF]
  is switched off (i.e. enters No Power mode) shall be retained and shall remain applicable
  when
  [CONDITION]
  powered on.
- kind: ordinary

###### 3.18.2.7.1 (Requirement Type)
Justification: The aim of this requirement is to limit the number of balise groups containing National Value information. Once a set of National Values has been received on-board, there is no need to re-load the information unless National Values change, the on-board equipment loses the information (failure situation), or the train enters an area requiring different National Values.
- WordTraceId: 280979
- atomic: false
- Legal Obligation: not applicable
- implement: false
- implementerEnhanced: Justification: The aim of this requirement is to limit the number of
  balise groups
  [EXTERNAL]
  containing National Value information. Once a set of National Values has been received on-board, there is no need to
  re-load
  [AGAIN]
  the information unless National Values change, the
  on-board equipment
  [SELF]
  loses the information (failure situation), or the train enters an area requiring different National Values.
- kind: Justification

##### 3.18.2.8 (Requirement Type)
The applicable set of National Values data shall be transmitted from the trackside on transition between areas requiring a different set of National Values.
- WordTraceId: 281366
- atomic: true
- Legal Obligation: mandatory
- implement: true
- implementerEnhanced: The applicable set of National Values data shall be transmitted from the
  trackside
  [EXTERNAL]
  on transition between areas requiring a different set of National Values.
- kind: ordinary

###### 3.18.2.8.1 (Requirement Type)
When a new set of National Values becomes applicable its content shall always overwrite the corresponding National Values currently applicable regardless of the country or region identifier(s).
- WordTraceId: 281523
- atomic: true
- Legal Obligation: mandatory
- implement: true
- implementerEnhanced: When
  [CONDITION]
  a new set of National Values becomes applicable its content shall always overwrite the corresponding National Values currently applicable regardless of the country or region identifier(s).
- kind: ordinary

##### 3.18.2.9 (Requirement Type)
A previously received set of National Values which is not yet applicable shall be deleted if:
- WordTraceId: 281717
- atomic: true
- Legal Obligation: mandatory
- implement: true
- implementerEnhanced: A previously received set of National Values which is
  not yet
  [TIME]
  applicable shall be deleted
  if
  [CONDITION]
  :
- kind: ordinary

###### 3.18.2.9.*[1] (Requirement Type)
a new set of National Values is received, or
- WordTraceId: 281811
- atomic: true
- Legal Obligation: mandatory (>= 1)
- implement: true
- ListNumberText: ·
- kind: ordinary

###### 3.18.2.9.*[2] (Requirement Type)
the ERTMS/ETCS on-board equipment is switched off (i.e., enters No Power mode).
- WordTraceId: 281856
- atomic: true
- Legal Obligation: mandatory (>= 1)
- implement: true
- implementerEnhanced: the
  ERTMS/ETCS on-board equipment
  [SELF]
  is switched off (i.e., enters No Power mode).
- ListNumberText: ·
- kind: ordinary

##### 3.18.2.10 (Requirement Type)
If a National Value becomes invalid, i.e., a mismatch has been detected between the country or region identifier read from a balise group and the corresponding identifier(s) of the applicable set with which the National Value was received and stored, then it shall be deleted.
- WordTraceId: 281936
- atomic: true
- Legal Obligation: mandatory
- implement: true
- implementerEnhanced: If
  [CONDITION]
  a National Value becomes invalid, i.e., a mismatch has been detected between the country or region identifier read from a
  balise group
  [EXTERNAL]
  and the corresponding identifier(s) of the applicable set with which the National Value was received and stored, then it shall be deleted.
- kind: ordinary

##### 3.18.2.11 (Requirement Type)
When a new set of National Values becomes applicable, any on-going supervision involving an overwritten National Value of type time or distance shall continue, but using the corresponding value from the new set. However, the starting location or starting time shall remain unchanged.
- WordTraceId: 282213
- atomic: false
- Legal Obligation: mandatory
- implement: true
- implementerEnhanced: When
  [CONDITION]
  a new set of National Values becomes applicable, any on-going supervision involving an overwritten National Value of type
  time
  [TIME]
  or distance shall continue, but using the corresponding value from the new set. However, the starting location or starting
  time
  [TIME]
  shall remain unchanged.
- kind: ordinary

#### 3.18.3 (Requirement Type)
Train Data
- WordTraceId: 282497
- atomic: false
- Legal Obligation: not applicable
- implement: false
- kind: Heading

##### 3.18.3.1 (Requirement Type)
Train Data shall neither be provided nor modified by ERTMS/ETCS trackside equipment.
- WordTraceId: 282509
- atomic: true
- Legal Obligation: mandatory
- implement: true
- implementerEnhanced: Train Data shall neither be provided nor modified by ERTMS/ETCS
  trackside
  [EXTERNAL]
  equipment.
- kind: ordinary

##### 3.18.3.2 (Requirement Type)
Before starting a mission, the following Train Data shall be acquired by the ERTMS/ETCS on-board equipment of a leading engine
- WordTraceId: 282594
- atomic: true
- Legal Obligation: not applicable
- implement: false
- implementerEnhanced: Before starting a mission, the following Train Data shall be acquired by the
  ERTMS/ETCS on-board equipment
  [SELF]
  of a leading engine
- kind: Heading

###### 3.18.3.2.a (Requirement Type)
Train category(ies)
- WordTraceId: 282721
- atomic: true
- Legal Obligation: mandatory
- implement: true
- ListNumberText: a)
- kind: ordinary

###### 3.18.3.2.b (Requirement Type)
Train length
- WordTraceId: 282741
- atomic: true
- Legal Obligation: mandatory
- implement: true
- ListNumberText: b)
- kind: ordinary

###### 3.18.3.2.c (Requirement Type)
Traction / brake parameters
- WordTraceId: 282754
- atomic: true
- Legal Obligation: mandatory
- implement: true
- ListNumberText: c)
- kind: ordinary

###### 3.18.3.2.d (Requirement Type)
Maximum train speed
- WordTraceId: 282782
- atomic: true
- Legal Obligation: mandatory
- implement: true
- ListNumberText: d)
- kind: ordinary

###### 3.18.3.2.e (Requirement Type)
Loading gauge
- WordTraceId: 282802
- atomic: true
- Legal Obligation: mandatory
- implement: true
- ListNumberText: e)
- kind: ordinary

###### 3.18.3.2.f (Requirement Type)
Axle load category
- WordTraceId: 282817
- atomic: true
- Legal Obligation: mandatory
- implement: true
- ListNumberText: f)
- kind: ordinary

###### 3.18.3.2.g (Requirement Type)
Traction system(s) accepted by the engine
- WordTraceId: 282836
- atomic: true
- Legal Obligation: mandatory
- implement: true
- ListNumberText: g)
- kind: ordinary

###### 3.18.3.2.h (Requirement Type)
Train fitted with airtight system
- WordTraceId: 282878
- atomic: true
- Legal Obligation: mandatory
- implement: true
- ListNumberText: h)
- kind: ordinary

###### 3.18.3.2.i (Requirement Type)
List of National Systems available on-board
- WordTraceId: 282913
- atomic: true
- Legal Obligation: mandatory
- implement: true
- ListNumberText: i)
- kind: ordinary

###### 3.18.3.2.j (Requirement Type)
Intentionally deleted
- WordTraceId: 282957
- atomic: false
- Legal Obligation: not applicable
- implement: false
- ListNumberText: j)
- kind: Placeholder

###### 3.18.3.2.k (Requirement Type)
Axle number
- WordTraceId: 282979
- atomic: true
- Legal Obligation: mandatory
- implement: true
- ListNumberText: k)
- kind: ordinary

###### 3.18.3.2.1 (Requirement Type)
The Train Data may come from ERTMS/ETCS external sources (e.g. the Train Interface), from pre-configured values or from the driver. .
- WordTraceId: 282992
- atomic: true
- Legal Obligation: mandatory
- implement: true
- implementerEnhanced: The Train Data may come from ERTMS/ETCS
  external
  [EXTERNAL]
  sources (
  e.g.
  [WEAK]
  the Train Interface), from pre-configured values or from the
  driver
  [EXTERNAL]
  . .
- kind: ordinary

###### 3.18.3.2.2 (Requirement Type)
Exception: The driver shall never be involved in the entry/ modification/validation of the Train Data “Traction system(s) accepted by the engine”, “List of National Systems available on-board” and “Axle number”.
- WordTraceId: 283126
- atomic: true
- Legal Obligation: mandatory
- implement: true
- implementerEnhanced: Exception: The
  driver
  [EXTERNAL]
  shall never be involved in the entry/ modification/validation of the Train Data “Traction system(s) accepted by the engine”, “List of National Systems available on-board” and “Axle number”.
- kind: ordinary

##### 3.18.3.3 (Requirement Type)
At standstill, it shall be possible for the driver to enter, modify and revalidate the Train Data that requires driver validation according to the specific train implementation.
- WordTraceId: 283338
- atomic: true
- Legal Obligation: mandatory
- implement: true
- implementerEnhanced: At standstill, it shall be possible for the
  driver
  [EXTERNAL]
  to enter, modify and
  revalidate
  [AGAIN]
  the Train Data that requires
  driver
  [EXTERNAL]
  validation according to the specific train implementation.
- kind: ordinary

###### 3.18.3.3.1 (Requirement Type)
In normal operation after the start of mission, if a train movement is detected while the driver is modifying or revalidating the Train Data, the ERTMS/ETCS on-board equipment shall trigger the brake command.
- WordTraceId: 283516
- atomic: true
- Legal Obligation: mandatory
- implement: true
- implementerEnhanced: In normal operation
  after
  [TIME]
  the start of mission,
  if
  [CONDITION]
  a train movement is detected
  while
  [TIME]
  the
  driver
  [EXTERNAL]
  is modifying or revalidating the Train Data, the
  ERTMS/ETCS on-board equipment
  [SELF]
  shall trigger the brake command.
- kind: ordinary

##### 3.18.3.4 (Requirement Type)
Following any entry/modification of Train Data when a communication session is already established or following the successful establishment of a communication session when valid Train Data are already available (e.g. when approaching a level 2/3 area or an accepting RBC area), the ERTMS/ETCS on-board equipment of the leading engine shall send the following set of Train Data to the RBC:
- WordTraceId: 283725
- atomic: true
- Legal Obligation: mandatory
- implement: true
- implementerEnhanced: Following any entry/modification of Train Data
  when
  [CONDITION]
  a communication session is already established or following the successful establishment of a communication session
  when
  [CONDITION]
  valid Train Data are already available (
  e.g.
  [WEAK]
  when
  [CONDITION]
  approaching a level 2/3 area or an accepting
  RBC
  [EXTERNAL]
  area), the
  ERTMS/ETCS on-board equipment
  [SELF]
  of the leading engine shall send the following set of Train Data to the
  RBC
  [EXTERNAL]
  :
- kind: ordinary

###### 3.18.3.4.a (Requirement Type)
Train category(ies).
- WordTraceId: 284115
- atomic: true
- Legal Obligation: mandatory
- implement: true
- ListNumberText: a)
- kind: ordinary

###### 3.18.3.4.b (Requirement Type)
Train length.
- WordTraceId: 284136
- atomic: true
- Legal Obligation: mandatory
- implement: true
- ListNumberText: b)
- kind: ordinary

###### 3.18.3.4.c (Requirement Type)
Maximum train speed.
- WordTraceId: 284151
- atomic: true
- Legal Obligation: mandatory
- implement: true
- ListNumberText: c)
- kind: ordinary

###### 3.18.3.4.d (Requirement Type)
Loading gauge.
- WordTraceId: 284172
- atomic: true
- Legal Obligation: mandatory
- implement: true
- ListNumberText: d)
- kind: ordinary

###### 3.18.3.4.e (Requirement Type)
Axle load category.
- WordTraceId: 284187
- atomic: true
- Legal Obligation: mandatory
- implement: true
- ListNumberText: e)
- kind: ordinary

###### 3.18.3.4.f (Requirement Type)
Traction system(s) accepted by the engine.
- WordTraceId: 284207
- atomic: true
- Legal Obligation: mandatory
- implement: true
- implementerEnhanced: Traction system(s) accepted by the engine
  [LINKED_PHRASE]
  .
- ListNumberText: f)
- kind: ordinary
- KnownTermLink -> 3.18.3.2.2

###### 3.18.3.4.g (Requirement Type)
Train fitted with airtight system.
- WordTraceId: 284250
- atomic: true
- Legal Obligation: mandatory
- implement: true
- ListNumberText: g)
- kind: ordinary

###### 3.18.3.4.h (Requirement Type)
List of National Systems available on-board
- WordTraceId: 284285
- atomic: true
- Legal Obligation: mandatory
- implement: true
- implementerEnhanced: List of National Systems available on-board
  [LINKED_PHRASE]
- ListNumberText: h)
- kind: ordinary
- KnownTermLink -> 3.18.3.2.2

###### 3.18.3.4.i (Requirement Type)
Axle number
- WordTraceId: 284329
- atomic: true
- Legal Obligation: mandatory
- implement: true
- implementerEnhanced: Axle number
  [LINKED_PHRASE]
- ListNumberText: i)
- kind: ordinary
- KnownTermLink -> 3.18.3.2.2

###### 3.18.3.4.1 (Requirement Type)
The RBC shall acknowledge the reception of this set of Train Data.
- WordTraceId: 284341
- atomic: true
- Legal Obligation: mandatory
- implement: true
- implementerEnhanced: The
  RBC
  [EXTERNAL]
  shall acknowledge the reception of this set of Train Data.
- kind: ordinary

###### 3.18.3.4.2 (Requirement Type)
In case the safe radio connection is lost before the acknowledgement is received, the Train Data shall be sent again once the safe radio connection has been re-established within the on-going communication session.
- WordTraceId: 284408
- atomic: true
- Legal Obligation: mandatory
- implement: true
- implementerEnhanced: In case
  [CONDITION]
  the safe radio connection is lost before the acknowledgement is received, the Train Data shall be sent
  again
  [LOOP]
  once the safe radio connection has been
  re-established
  [AGAIN]
  within the on-going communication session.
- kind: ordinary

##### 3.18.3.5 (Requirement Type)
Intentionally deleted.
- WordTraceId: 284623
- atomic: false
- Legal Obligation: not applicable
- implement: false
- kind: Placeholder

##### 3.18.3.6 (Requirement Type)
For modification of Train Data, which is/are affected by a change of input information from the ERTMS/ETCS on-board equipment external interface, refer to procedure "Changing Train Data from sources different from the driver" described in section 5.17.
- WordTraceId: 284646
- atomic: true
- Legal Obligation: unknown
- implement: true
- implementerEnhanced: For modification of Train Data, which is/are affected by a change of input information from the
  ERTMS/ETCS on-board equipment
  [SELF]
  external interface
  [EXTERNAL]
  , refer to procedure "
  Changing Train Data from sources different from the
  driver
  [EXTERNAL]
  [LINKED_PHRASE]
  " described in section 5.17.
- kind: ordinary
- CrossRefLink -> 5.17
- KnownTermLink -> 3.14.1.7.2

##### 3.18.3.7 (Requirement Type)
In case the Train Data regarding train category, axle load category, loading gauge or traction system has been changed and the train is at standstill:
- WordTraceId: 284899
- atomic: true
- Legal Obligation: unknown
- implement: false
- implementerEnhanced: In case
  [CONDITION]
  the Train Data regarding train category, axle load category, loading gauge or traction system has been changed and the train is at standstill:
- kind: Heading

###### 3.18.3.7.a (Requirement Type)
the location based information stored on-board shall be shortened to the current position of the train. Refer to appendix A.3.4 for the exhaustive list of information, which shall be shortened.
- WordTraceId: 285050
- atomic: false
- Legal Obligation: mandatory
- implement: true
- ListNumberText: a)
- kind: ordinary
- CrossRefLink -> A.3.4

###### 3.18.3.7.b (Requirement Type)
the stored MA, linking and track description, which have been received from the RBC after a level 2/3 transition or a RBC transition for a further location has been ordered, shall be deleted.
- WordTraceId: 285244
- atomic: true
- Legal Obligation: mandatory
- implement: true
- implementerEnhanced: the stored MA, linking and track description, which have been received from the
  RBC
  [EXTERNAL]
  after
  [TIME]
  a level 2/3 transition or a
  RBC
  [EXTERNAL]
  transition for a further location has been ordered, shall be deleted.
- ListNumberText: b)
- kind: ordinary

##### 3.18.3.8 (Requirement Type)
In case the Train Data regarding train length has been increased, the currently used track description, if any, shall be considered as unknown in rear of the former min safe rear end of the train.
- WordTraceId: 285436
- atomic: true
- Legal Obligation: mandatory
- implement: true
- implementerEnhanced: In case
  [CONDITION]
  the Train Data regarding train length has been increased, the currently used track description,
  if
  [CONDITION]
  any, shall be considered as unknown in rear of the former min safe rear end of the train.
- kind: ordinary

#### 3.18.4 (Requirement Type)
Additional Data
- WordTraceId: 285633
- atomic: false
- Legal Obligation: not applicable
- implement: false
- kind: Heading

##### 3.18.4.1 (Requirement Type)
Driver ID
- WordTraceId: 285649
- atomic: false
- Legal Obligation: not applicable
- implement: false
- kind: Heading

###### 3.18.4.1.1 (Requirement Type)
The driver ID shall be used to identify the responsible person for operating an active desk.
- WordTraceId: 285659
- atomic: true
- Legal Obligation: mandatory
- implement: true
- kind: ordinary

###### 3.18.4.1.1.1 (Requirement Type)
Note: This data is used for recording purposes only.
- WordTraceId: 285752
- atomic: false
- Legal Obligation: not applicable
- implement: false
- kind: Note

###### 3.18.4.1.2 (Requirement Type)
If allowed by a National value, it shall be possible for the driver to change driver ID while the train is running.
- WordTraceId: 285805
- atomic: true
- Legal Obligation: mandatory
- implement: true
- implementerEnhanced: If
  [CONDITION]
  allowed by a National value, it shall be possible for the
  driver
  [EXTERNAL]
  to change driver ID
  while
  [TIME]
  the train is running.
- kind: ordinary

###### 3.18.4.1.3 (Requirement Type)
It shall be possible to enter driver ID also in a non-leading engine.
- WordTraceId: 285921
- atomic: true
- Legal Obligation: mandatory
- implement: true
- kind: ordinary

##### 3.18.4.2 (Requirement Type)
ERTMS/ETCS Level
- WordTraceId: 285991
- atomic: false
- Legal Obligation: not applicable
- implement: false
- kind: Heading

###### 3.18.4.2.1 (Requirement Type)
The driver shall have the possibility to enter the ERTMS/ETCS level during a start of a mission.
- WordTraceId: 286008
- atomic: true
- Legal Obligation: mandatory
- implement: true
- implementerEnhanced: The
  driver
  [EXTERNAL]
  shall have the possibility to enter the ERTMS/ETCS level
  during
  [TIME]
  a start of a mission.
- kind: ordinary

###### 3.18.4.2.2 (Requirement Type)
The ERTMS/ETCS level information is required for train operation except sleeping mode.
- WordTraceId: 286105
- atomic: true
- Legal Obligation: unknown
- implement: true
- kind: ordinary

###### 3.18.4.2.3 (Requirement Type)
In normal operation after the start of mission the driver shall not have to select the ERTMS/ETCS level (all other level transitions are executed automatically).
- WordTraceId: 286192
- atomic: true
- Legal Obligation: mandatory
- implement: true
- implementerEnhanced: In normal operation
  after
  [TIME]
  the start of mission the
  driver
  [EXTERNAL]
  shall not have to select the ERTMS/ETCS level (all other level transitions are executed automatically).
- kind: ordinary

###### 3.18.4.2.4 (Requirement Type)
For operational fallback situations: at standstill, the onboard equipment shall allow the driver to change the ERTMS/ETCS level..
- WordTraceId: 286355
- atomic: true
- Legal Obligation: mandatory
- implement: true
- implementerEnhanced: For operational fallback situations: at standstill, the
  onboard equipment
  [SELF]
  shall allow the
  driver
  [EXTERNAL]
  to change the ERTMS/ETCS level..
- kind: ordinary

###### 3.18.4.2.4.1 (Requirement Type)
Intentionally deleted.
- WordTraceId: 286485
- atomic: false
- Legal Obligation: not applicable
- implement: false
- kind: Placeholder

###### 3.18.4.2.5 (Requirement Type)
If the table of supported levels given by trackside is available, the selection of level by the driver shall be limited to those contained in this table. If the table of trackside supported levels is not available, the driver can select any level within a default list configured on-board.
- WordTraceId: 286508
- atomic: false
- Legal Obligation: mandatory
- implement: true
- implementerEnhanced: If
  [CONDITION]
  the table of supported levels given by
  trackside
  [EXTERNAL]
  is available, the selection of level by the
  driver
  [EXTERNAL]
  shall be limited to those contained in this table.
  If
  [CONDITION]
  the table of
  trackside
  [EXTERNAL]
  supported levels is not available, the
  driver
  [EXTERNAL]
  can select any level within a default list configured on-board.
- kind: ordinary

##### 3.18.4.3 (Requirement Type)
Radio Network identification / RBC Identification / Telephone Number
- WordTraceId: 286798
- atomic: false
- Legal Obligation: not applicable
- implement: false
- kind: Heading

###### 3.18.4.3.1 (Requirement Type)
Note: If a valid RBC identity and telephone number is available on-board, no driver data entry is needed to establish a connection to the RBC.
- WordTraceId: 286867
- atomic: false
- Legal Obligation: not applicable
- implement: false
- implementerEnhanced: Note:
  If
  [CONDITION]
  a valid RBC identity and telephone number is available on-board, no
  driver
  [EXTERNAL]
  data entry is needed to establish a connection to the
  RBC
  [EXTERNAL]
  .
- kind: Note

###### 3.18.4.3.2 (Requirement Type)
If the driver enters level 2/3, at start of mission, the ERTMS/ETCS on-board equipment shall offer the driver different means to select the RBC contact information (including RBC identity, RBC telephone number, and the identity of the radio network to be used), for details see chapter 5, Start of Mission procedure.
- WordTraceId: 287011
- atomic: true
- Legal Obligation: mandatory
- implement: true
- implementerEnhanced: If
  [CONDITION]
  the
  driver
  [EXTERNAL]
  enters level 2/3, at start of mission, the
  ERTMS/ETCS on-board equipment
  [SELF]
  shall offer the
  driver
  [EXTERNAL]
  different means to select the
  RBC
  [EXTERNAL]
  contact information (including RBC identity,
  RBC
  [EXTERNAL]
  telephone number, and the identity of the radio network to be used), for details see chapter 5, Start of Mission procedure.
- kind: ordinary

###### 3.18.4.3.3 (Requirement Type)
In normal operation after the start of mission, the driver shall have no further possibility to modify the RBC contact information (all further modifications of this data are executed automatically). Exception: after a manual level change to level 2/3 and if either no Mobile Terminal is registered to a Radio Network or no valid RBC-ID/phone number is available, the ERTMS/ETCS on-board equipment shall request the driver to select the RBC contact information by the same means as for Start of Mission.
- WordTraceId: 287328
- atomic: false
- Legal Obligation: mandatory
- implement: true
- implementerEnhanced: In normal operation
  after
  [TIME]
  the start of mission, the
  driver
  [EXTERNAL]
  shall have no further possibility to modify the
  RBC
  [EXTERNAL]
  contact information (all further modifications of this data are executed automatically). Exception:
  after
  [TIME]
  a manual level change to level 2/3 and
  if
  [CONDITION]
  either no Mobile Terminal is registered to a Radio Network or no valid RBC-ID/phone number is available, the
  ERTMS/ETCS on-board equipment
  [SELF]
  shall request the
  driver
  [EXTERNAL]
  to select the
  RBC
  [EXTERNAL]
  contact information by the same means as for Start of Mission.
- kind: ordinary

###### 3.18.4.3.4 (Requirement Type)
If the driver selects “Use of EIRENE short number” to contact the RBC and the communication session is successfully established, the ERTMS/ETCS on-board equipment shall store as valid RBC identity and telephone number, the RBC identity reported by EURORADIO and the EIRENE short number, respectively.
- WordTraceId: 287832
- atomic: true
- Legal Obligation: mandatory
- implement: true
- implementerEnhanced: If
  [CONDITION]
  the
  driver
  [EXTERNAL]
  selects “Use of EIRENE short number” to contact the
  RBC
  [EXTERNAL]
  and the communication session is successfully established, the
  ERTMS/ETCS on-board equipment
  [SELF]
  shall store as valid RBC identity and telephone number, the RBC identity reported by EURORADIO and the EIRENE short number, respectively.
- kind: ordinary

###### 3.18.4.3.4.1 (Requirement Type)
Note: If the short number is re-used by the ERTMS/ETCS on-board equipment (e.g. following a loss of safe radio connection) and does not direct to a RBC with the stored RBC ID, the connection will be terminated (EURORADIO functionality).
- WordTraceId: 288133
- atomic: false
- Legal Obligation: not applicable
- implement: false
- implementerEnhanced: Note:
  If
  [CONDITION]
  the short number is
  re-used
  [AGAIN]
  by the
  ERTMS/ETCS on-board equipment
  [SELF]
  (
  e.g.
  [WEAK]
  following a loss of safe radio connection) and does not direct to a
  RBC
  [EXTERNAL]
  with the stored RBC ID, the connection will be terminated (EURORADIO functionality).
- kind: Note

##### 3.18.4.4 (Requirement Type)
ETCS Identity
- WordTraceId: 288370
- atomic: false
- Legal Obligation: not applicable
- implement: false
- kind: Heading

###### 3.18.4.4.1 (Requirement Type)
The ETCS identity of an on-board equipment is made of a single identity number. The ETCS identity of an RBC, balise group, loop or RIU is composed of a country/region identity number and of an identity number within the country/region.
- WordTraceId: 288384
- atomic: false
- Legal Obligation: unknown
- implement: true
- implementerEnhanced: The ETCS identity of an
  on-board equipment
  [SELF]
  is made of a single identity number. The ETCS identity of an
  RBC
  [EXTERNAL]
  ,
  balise group
  [EXTERNAL]
  ,
  loop
  [EXTERNAL]
  or
  RIU
  [EXTERNAL]
  is composed of a country/region identity number and of an identity number within the country/region.
- kind: ordinary

###### 3.18.4.4.2 (Requirement Type)
All on-board equipments in service, balise groups marked as linked, RBC’s, RIU’s, and loops shall be assigned a unique ETCS identity within their respective group.
- WordTraceId: 288620
- atomic: true
- Legal Obligation: mandatory
- implement: true
- implementerEnhanced: All on-board equipments in service,
  balise groups
  [EXTERNAL]
  marked as linked, RBC’s, RIU’s, and
  loops
  [EXTERNAL]
  shall be assigned a unique ETCS identity within their respective group.
- kind: ordinary

###### 3.18.4.4.3 (Requirement Type)
The assignment of (unique or not) ETCS identities to balise groups marked as unlinked is the sole responsibility of the entity in charge of the assignment of values (see SUBSET-054), depending on the specific trackside implementation.
- WordTraceId: 288784
- atomic: true
- Legal Obligation: unknown
- implement: true
- implementerEnhanced: The assignment of (unique or not) ETCS identities to
  balise groups
  [EXTERNAL]
  marked as unlinked is the sole responsibility of the entity in charge of the assignment of values (see SUBSET-054), depending on the specific
  trackside
  [EXTERNAL]
  implementation.
- kind: ordinary

##### 3.18.4.5 (Requirement Type)
Train Running Number
- WordTraceId: 289019
- atomic: false
- Legal Obligation: not applicable
- implement: false
- kind: Heading

###### 3.18.4.5.1 (Requirement Type)
During the Start of Mission, the ERTMS/ETCS on-board equipment of a leading engine shall acquire the train running number from driver input, from the RBC or from other ERTMS/ETCS external sources.
- WordTraceId: 289040
- atomic: true
- Legal Obligation: mandatory
- implement: true
- implementerEnhanced: During
  [TIME]
  the Start of Mission, the
  ERTMS/ETCS on-board equipment
  [SELF]
  of a leading engine shall acquire the train running number from
  driver
  [EXTERNAL]
  input, from the
  RBC
  [EXTERNAL]
  or from other ERTMS/ETCS
  external
  [EXTERNAL]
  sources.
- kind: ordinary

###### 3.18.4.5.2 (Requirement Type)
It shall be possible to enter train running number also in a non-leading engine.
- WordTraceId: 289237
- atomic: true
- Legal Obligation: mandatory
- implement: true
- kind: ordinary

###### 3.18.4.5.3 (Requirement Type)
It shall be possible to change the train running number while running, from driver input, from the RBC or from other ERTMS/ETCS external sources.
- WordTraceId: 289318
- atomic: true
- Legal Obligation: mandatory
- implement: true
- implementerEnhanced: It shall be possible to change the train running number
  while
  [TIME]
  running, from
  driver
  [EXTERNAL]
  input, from the
  RBC
  [EXTERNAL]
  or from other ERTMS/ETCS
  external
  [EXTERNAL]
  sources.
- kind: ordinary

###### 3.18.4.5.4 (Requirement Type)
Following any entry/modification of the train running number when a communication session is already established or following the successful establishment of a communication session when valid train running number is already available, the ERTMS/ETCS on-board equipment shall send the train running number to the RBC.
- WordTraceId: 289464
- atomic: true
- Legal Obligation: mandatory
- implement: true
- implementerEnhanced: Following any entry/modification of the train running number
  when
  [CONDITION]
  a communication session is already established or following the successful establishment of a communication session
  when
  [CONDITION]
  valid train running number is already available, the
  ERTMS/ETCS on-board equipment
  [SELF]
  shall send the train running number to the
  RBC
  [EXTERNAL]
  .
- kind: ordinary

###### 3.18.4.5.4.1 (Requirement Type)
Exception: if the train running number has been received from the RBC, it shall not be sent back to the RBC by the ERTMS/ETCS on-board equipment.
- WordTraceId: 289782
- atomic: true
- Legal Obligation: mandatory
- implement: true
- implementerEnhanced: Exception:
  if
  [CONDITION]
  the train running number has been received from the
  RBC
  [EXTERNAL]
  , it shall not be sent back to the
  RBC
  [EXTERNAL]
  by the
  ERTMS/ETCS on-board equipment
  [SELF]
  .
- kind: ordinary

##### 3.18.4.6 (Requirement Type)
Adhesion Factor
- WordTraceId: 289928
- atomic: false
- Legal Obligation: not applicable
- implement: false
- kind: Heading

###### 3.18.4.6.1 (Requirement Type)
The adhesion factor shall be used to adjust the emergency brake model of the train (see 3.13).
- WordTraceId: 289944
- atomic: true
- Legal Obligation: mandatory
- implement: true
- kind: ordinary
- CrossRefLink -> 3.13

###### 3.18.4.6.2 (Requirement Type)
The adhesion factor may be changed while the train is running.
- WordTraceId: 290040
- atomic: true
- Legal Obligation: optional
- implement: true
- implementerEnhanced: The adhesion factor may be changed
  while
  [TIME]
  the train is running.
- kind: ordinary

###### 3.18.4.6.2.1 (Requirement Type)
It shall be possible to update the adhesion factor from trackside and - if permitted by a National value - by the driver. If, following a change of National Values, the update of the adhesion factor is no more permitted to the driver, the adhesion factor previously modified by the driver to slippery rail shall immediately be reset to non slippery rail. Any trackside adhesion profile is not affected.
- WordTraceId: 290103
- atomic: false
- Legal Obligation: mandatory
- implement: true
- implementerEnhanced: It shall be possible to update the adhesion factor from
  trackside
  [EXTERNAL]
  and -
  if
  [CONDITION]
  permitted by a National value - by the
  driver
  [EXTERNAL]
  .
  If
  [CONDITION]
  , following a change of National Values, the update of the adhesion factor is no more permitted to the
  driver
  [EXTERNAL]
  , the adhesion factor previously modified by the
  driver
  [EXTERNAL]
  to slippery rail shall
  immediately
  [WEAK]
  be reset to non slippery rail. Any
  trackside
  [EXTERNAL]
  adhesion profile is not affected.
- kind: ordinary

###### 3.18.4.6.2.2 (Requirement Type)
The adhesion factor shall be sent as profile data from trackside when needed.
- WordTraceId: 290506
- atomic: true
- Legal Obligation: mandatory
- implement: true
- implementerEnhanced: The adhesion factor shall be sent as profile data from
  trackside
  [EXTERNAL]
  when
  [CONDITION]
  needed
  [WEAK]
  .
- kind: ordinary

###### 3.18.4.6.2.3 (Requirement Type)
The driver shall be informed whether the value of the adhesion factor is “slippery rail”.
- WordTraceId: 290584
- atomic: true
- Legal Obligation: mandatory
- implement: true
- implementerEnhanced: The
  driver
  [EXTERNAL]
  shall be informed
  whether
  [CONDITION]
  the value of the adhesion factor is “slippery rail”.
- kind: ordinary

###### 3.18.4.6.3 (Requirement Type)
The selection of the adhesion value from trackside or by driver entry shall be limited to the options slippery rail/ non slippery rail.
- WordTraceId: 290674
- atomic: true
- Legal Obligation: mandatory
- implement: true
- implementerEnhanced: The selection of the adhesion value from
  trackside
  [EXTERNAL]
  or by
  driver
  [EXTERNAL]
  entry shall be limited to the options
  slippery rail
  [LINKED_PHRASE]
  / non
  slippery rail
  [LINKED_PHRASE]
  .
- kind: ordinary
- KnownTermLink -> 3.18.4.6.2.3

###### 3.18.4.6.3.1 (Requirement Type)
Intentionally deleted.
- WordTraceId: 290810
- atomic: false
- Legal Obligation: not applicable
- implement: false
- kind: Placeholder

###### 3.18.4.6.4 (Requirement Type)
The default value for the adhesion factor shall be the highest value (i.e. not slippery rail).
- WordTraceId: 290833
- atomic: true
- Legal Obligation: mandatory
- implement: true
- implementerEnhanced: The default value for the adhesion factor shall be the highest value (i.e. not
  slippery rail
  [LINKED_PHRASE]
  ).
- kind: ordinary
- KnownTermLink -> 3.18.4.6.2.3

###### 3.18.4.6.5 (Requirement Type)
Intentionally deleted.
- WordTraceId: 290928
- atomic: false
- Legal Obligation: not applicable
- implement: false
- kind: Placeholder

#### 3.18.5 (Requirement Type)
Date and Time
- WordTraceId: 290951
- atomic: false
- Legal Obligation: not applicable
- implement: false
- implementerEnhanced: Date and
  Time
  [TIME]
- kind: Heading

##### 3.18.5.1 (Requirement Type)
Each ERTMS/ETCS on-board equipment shall be able to provide the date (day, month, year) and time (hour, minute, second) in Universal Time Co-ordinated (UTC) and Local Time.
- WordTraceId: 290965
- atomic: true
- Legal Obligation: mandatory
- implement: true
- implementerEnhanced: Each
  ERTMS/ETCS on-board equipment
  [SELF]
  shall be able to provide the date (day, month, year) and
  time
  [TIME]
  (hour, minute, second) in Universal
  Time
  [TIME]
  Co-ordinated (UTC) and Local
  Time
  [TIME]
  .
- kind: ordinary

##### 3.18.5.2 (Requirement Type)
The local time shall be presented to the driver, while the UTC shall be used for the juridical data.
- WordTraceId: 291138
- atomic: false
- Legal Obligation: mandatory
- implement: true
- implementerEnhanced: The local
  time
  [TIME]
  shall be presented to the
  driver
  [EXTERNAL]
  ,
  while
  [TIME]
  the UTC shall be used for the juridical data.
- kind: ordinary

##### 3.18.5.3 (Requirement Type)
Deleted.
- WordTraceId: 291239
- atomic: false
- Legal Obligation: not applicable
- implement: false
- kind: Placeholder

#### 3.18.6 (Requirement Type)
Data view
- WordTraceId: 291248
- atomic: false
- Legal Obligation: not applicable
- implement: false
- kind: Heading

##### 3.18.6.1 (Requirement Type)
Outside the context of data entry, the ERTMS/ETCS on-board equipment shall offer the possibility to the driver to view the driver ID, the train running number, the RBC contact information, the Virtual Balise Cover(s) and the Train Data either modifiable by the driver or modifiable by other ERTMS/ETCS external sources.
- WordTraceId: 291258
- atomic: true
- Legal Obligation: mandatory
- implement: true
- implementerEnhanced: Outside the context of data entry, the
  ERTMS/ETCS on-board equipment
  [SELF]
  shall offer the possibility to the
  driver
  [EXTERNAL]
  to view the driver ID, the train running number, the
  RBC
  [EXTERNAL]
  contact information, the Virtual
  Balise
  [EXTERNAL]
  Cover(s) and the Train Data either modifiable by the
  driver
  [EXTERNAL]
  or modifiable by other ERTMS/ETCS
  external
  [EXTERNAL]
  sources.
- kind: ordinary

##### 3.18.6.2 (Requirement Type)
Only valid data shall be presented to the driver.
- WordTraceId: 291578
- atomic: true
- Legal Obligation: mandatory
- implement: true
- implementerEnhanced: Only valid data shall be presented to the
  driver
  [EXTERNAL]
  .
- kind: ordinary

### 3.19 (Requirement Type)
Intentionally deleted
- WordTraceId: 291628
- atomic: false
- Legal Obligation: not applicable
- implement: false
- kind: Placeholder

### 3.20 (Requirement Type)
Juridical Data
- WordTraceId: 291650
- atomic: false
- Legal Obligation: not applicable
- implement: false
- kind: Heading

#### 3.20.1 (Requirement Type)
PLACEHOLDER REQUIREMENT - DO NOT TRACE
- WordTraceId: 291665
- atomic: false
- Legal Obligation: not applicable
- implement: false
- kind: Placeholder

##### 3.20.1.1 (Requirement Type)
The on-board recording device of the train is not part of the ERTMS/ETCS on-board equipment..
- WordTraceId: 291665
- atomic: true
- Legal Obligation: unknown
- implement: true
- implementerEnhanced: The on-board recording device of the train is not part of the
  ERTMS/ETCS on-board equipment
  [SELF]
  ..
- kind: ordinary

##### 3.20.1.2 (Requirement Type)
The ERTMS/ETCS on-board equipment shall transmit to the on-board recording device the information that may be used for legal purpose after hazardous situations.
- WordTraceId: 291759
- atomic: false
- Legal Obligation: mixed
- implement: true
- implementerEnhanced: The
  ERTMS/ETCS on-board equipment
  [SELF]
  shall transmit to the on-board recording device the information that may be used for legal purpose
  after
  [TIME]
  hazardous situations.
- kind: ordinary

###### 3.20.1.2.1 (Requirement Type)
For details about data messages that shall be transmitted to the on-board recording device and their related triggering events, refer to SUBSET-027.
- WordTraceId: 291920
- atomic: true
- Legal Obligation: mandatory
- implement: true
- kind: ordinary

##### 3.20.1.3 (Requirement Type)
Intentionally deleted.
- WordTraceId: 292069
- atomic: false
- Legal Obligation: not applicable
- implement: false
- kind: Placeholder

##### 3.20.1.4 (Requirement Type)
Intentionally deleted.
- WordTraceId: 292092
- atomic: false
- Legal Obligation: not applicable
- implement: false
- kind: Placeholder

##### 3.20.1.5 (Requirement Type)
Intentionally deleted.
- WordTraceId: 292115
- atomic: false
- Legal Obligation: not applicable
- implement: false
- kind: Placeholder

##### 3.20.1.6 (Requirement Type)
Intentionally deleted.
- WordTraceId: 292138
- atomic: false
- Legal Obligation: not applicable
- implement: false
- kind: Placeholder

##### 3.20.1.7 (Requirement Type)
Intentionally deleted.
- WordTraceId: 292161
- atomic: false
- Legal Obligation: not applicable
- implement: false
- kind: Placeholder

##### 3.20.1.8 (Requirement Type)
Intentionally deleted.
- WordTraceId: 292184
- atomic: false
- Legal Obligation: not applicable
- implement: false
- kind: Placeholder

##### 3.20.1.9 (Requirement Type)
Intentionally deleted.
- WordTraceId: 292207
- atomic: false
- Legal Obligation: not applicable
- implement: false
- kind: Placeholder

## A (Requirement Type)
PLACEHOLDER REQUIREMENT - DO NOT TRACE
- WordTraceId: 292230
- atomic: false
- Legal Obligation: not applicable
- implement: false
- kind: Placeholder

### A.3 (Requirement Type)
Appendix to Chapter 3
- WordTraceId: 292230
- atomic: false
- Legal Obligation: not applicable
- implement: false
- kind: Heading

#### A.3.1 (Requirement Type)
A.3.1 List of Fixed Value Data
- WordTraceId: 292252
- atomic: false
- Legal Obligation: not applicable
- PlainText: List of Fixed Value Data
- implement: true
- implementerEnhanced: List of Fixed Value Data
- kind: ordinary

#### A.3.1[2] (Requirement Type)
- WordTraceId: 292284
- atomic: false
- Legal Obligation: not applicable
- implement: false
- kind: Placeholder

##### A.3.1[2].[t]* (Requirement Type)
| Fixed Value Data | Value | Name |
| --- | --- | --- |
| [r][2].Data The number of times to try to establish a safe radio connection. | [r][2].Value 3 times | [r][2].Name |
| [r][3].Data Repetition of radio messages (i.e. excluding the first sending) | [r][3].Value 3 times | [r][3].Name |
| [r][4].Data Waiting time before radio message repetition | [r][4].Value 15 s | [r][4].Name |
| [r][5].Data Speed difference between Permitted speed and Emergency Brake Intervention supervision limits, minimum value | [r][5].Value 7.5 km/h | [r][5].Name dV_ebi_min |
| [r][6].Data Speed difference between Permitted speed and Emergency Brake Intervention supervision limits, maximum value | [r][6].Value 15 km/h | [r][6].Name dV_ebi_max |
| [r][7].Data Value of MRSP where dV_ebi starts to increase to dV_ebi_max | [r][7].Value 110 km/h | [r][7].Name V_ebi_min |
| [r][8].Data Value of MRSP where dV_ebi stops to increase to dV_ebi_max | [r][8].Value 210 km/h | [r][8].Name V_ebi_max |
| [r][9].Data Speed difference between Permitted speed and Service Brake Intervention supervision limits, minimum value | [r][9].Value 5.5 km/h | [r][9].Name dV_sbi_min |
| [r][10].Data Speed difference between Permitted speed and Service Brake Intervention supervision limits, maximum value | [r][10].Value 10 km/h | [r][10].Name dV_sbi_max |
| [r][11].Data Value of MRSP where dV_sbi starts to increase to dV_sbi_max | [r][11].Value 110 km/h | [r][11].Name V_sbi_min |
| [r][12].Data Value of MRSP where dV_sbi stops to increase to dV_sbi_max | [r][12].Value 210 km/h | [r][12].Name V_sbi_max |
| [r][13].Data Speed difference between Permitted speed and Warning supervision limits, minimum value | [r][13].Value 4 km/h | [r][13].Name dV_warning_min |
| [r][14].Data Speed difference between Permitted speed and Warning supervision limits, maximum value | [r][14].Value 5 km/h | [r][14].Name dV_warning_max |
| [r][15].Data Value of MRSP where dV_warning starts to increase to dV_warning_max | [r][15].Value 110 km/h | [r][15].Name V_warning_min |
| [r][16].Data Value of MRSP where dV_warning stops to increase to dV_warning_max | [r][16].Value 140 km/h | [r][16].Name V_warning_max |
| [r][17].Data Time between Warning supervision limit and FLOI | [r][17].Value 2 s | [r][17].Name T_warning |
| [r][18].Data Driver reaction time between Permitted speed supervision limit and FLOI | [r][18].Value 4 s | [r][18].Name T_driver |
| [r][19].Data Time between the pre-indication location and the indication supervision limit valid for MRSP speed. | [r][19].Value 7 s | [r][19].Name T_preindication |
| [r][20].Data Maximum possible rotating mass as a percentage of the total weight of the train | [r][20].Value 15 % | [r][20].Name M_rotating_max |
| [r][21].Data Minimum possible rotating mass as a percentage of the total weight of the train | [r][21].Value 2 % | [r][21].Name M_rotating_min |
| [r][22].Data Compensation of the speed measurement inaccuracy used for the calculation of speed restriction to ensure given permitted braking distance | [r][22].Value 5 km/h | [r][22].Name |
| [r][23].Data MA request repetition cycle, default value | [r][23].Value 60 s | [r][23].Name T CYCRQSTD |
| [r][24].Data Mode transitions: Driver acknowledgement time | [r][24].Value 5 s | [r][24].Name T ACK |
| [r][25].Data Maximum time to maintain a communication session in case of failed re-connection attempts | [r][25].Value 5 minutes | [r][25].Name |
| [r][26].Data Distance of metal immunity in Levels 0/NTC | [r][26].Value 300 metres | [r][26].Name D_Metal |
| [r][27].Data Driver reaction time before sounding the horn | [r][27].Value 4 s | [r][27].Name |
| [r][28].Data Time between minimum safe rear end of the train leaving a track condition area and on-board deleting the applicable indication | [r][28].Value 5 s | [r][28].Name |
| [r][29].Data Distance to keep on-board information in rear of the min safe rear end of the train | [r][29].Value 300 metres | [r][29].Name |
| [r][30].Data Additional delay time to disconnection on supervision of safe radio connection | [r][30].Value 60 s | [r][30].Name |
| [r][31].Data “Connection status” timer for safe radio connection indication | [r][31].Value 45 s | [r][31].Name |
- WordTraceId: 295084
- atomic: false
- Legal Obligation: not applicable
- implement: false
- kind: Table

###### A.3.1[2].[t]*.[r][2] (Requirement Type)
- WordTraceId: 292314
- atomic: false
- Legal Obligation: not applicable
- implement: false
- kind: Table

###### A.3.1[2].[t]*.[r][2].Data (Requirement Type)
The number of times to try to establish a safe radio connection.
- WordTraceId: 292314
- atomic: true
- Legal Obligation: unknown
- implement: true
- kind: ordinary

###### A.3.1[2].[t]*.[r][2].Value (Requirement Type)
3 times
- WordTraceId: 292380
- atomic: true
- Legal Obligation: unknown
- implement: true
- kind: ordinary

###### A.3.1[2].[t]*.[r][2].Name (Requirement Type)
- WordTraceId: 292388
- atomic: true
- Legal Obligation: unknown
- implement: true
- kind: ordinary

###### A.3.1[2].[t]*.[r][3] (Requirement Type)
- WordTraceId: 292390
- atomic: false
- Legal Obligation: not applicable
- implement: false
- kind: Table

###### A.3.1[2].[t]*.[r][3].Data (Requirement Type)
Repetition of radio messages (i.e. excluding the first sending)
- WordTraceId: 292390
- atomic: true
- Legal Obligation: unknown
- implement: true
- implementerEnhanced: Repetition
  [LOOP]
  of radio messages (i.e. excluding the first sending)
- kind: ordinary

###### A.3.1[2].[t]*.[r][3].Value (Requirement Type)
3 times
- WordTraceId: 292454
- atomic: true
- Legal Obligation: unknown
- implement: true
- kind: ordinary

###### A.3.1[2].[t]*.[r][3].Name (Requirement Type)
- WordTraceId: 292462
- atomic: true
- Legal Obligation: unknown
- implement: true
- kind: ordinary

###### A.3.1[2].[t]*.[r][4] (Requirement Type)
- WordTraceId: 292464
- atomic: false
- Legal Obligation: not applicable
- implement: false
- kind: Table

###### A.3.1[2].[t]*.[r][4].Data (Requirement Type)
Waiting time before radio message repetition
- WordTraceId: 292464
- atomic: true
- Legal Obligation: unknown
- implement: true
- implementerEnhanced: Waiting time
  [TIME]
  before radio message
  repetition
  [LOOP]
- kind: ordinary

###### A.3.1[2].[t]*.[r][4].Value (Requirement Type)
15 s
- WordTraceId: 292509
- atomic: true
- Legal Obligation: unknown
- implement: true
- kind: ordinary

###### A.3.1[2].[t]*.[r][4].Name (Requirement Type)
- WordTraceId: 292514
- atomic: true
- Legal Obligation: unknown
- implement: true
- kind: ordinary

###### A.3.1[2].[t]*.[r][5] (Requirement Type)
- WordTraceId: 292516
- atomic: false
- Legal Obligation: not applicable
- implement: false
- kind: Table

###### A.3.1[2].[t]*.[r][5].Data (Requirement Type)
Speed difference between Permitted speed and Emergency Brake Intervention supervision limits, minimum value
- WordTraceId: 292516
- atomic: true
- Legal Obligation: unknown
- implement: true
- kind: ordinary

###### A.3.1[2].[t]*.[r][5].Value (Requirement Type)
7.5 km/h
- WordTraceId: 292624
- atomic: true
- Legal Obligation: unknown
- implement: true
- kind: ordinary

###### A.3.1[2].[t]*.[r][5].Name (Requirement Type)
dV_ebi_min
- WordTraceId: 292633
- atomic: true
- Legal Obligation: unknown
- implement: true
- kind: ordinary

###### A.3.1[2].[t]*.[r][6] (Requirement Type)
- WordTraceId: 292645
- atomic: false
- Legal Obligation: not applicable
- implement: false
- kind: Table

###### A.3.1[2].[t]*.[r][6].Data (Requirement Type)
Speed difference between Permitted speed and Emergency Brake Intervention supervision limits, maximum value
- WordTraceId: 292645
- atomic: true
- Legal Obligation: unknown
- implement: true
- kind: ordinary

###### A.3.1[2].[t]*.[r][6].Value (Requirement Type)
15 km/h
- WordTraceId: 292753
- atomic: true
- Legal Obligation: unknown
- implement: true
- kind: ordinary

###### A.3.1[2].[t]*.[r][6].Name (Requirement Type)
dV_ebi_max
- WordTraceId: 292761
- atomic: true
- Legal Obligation: unknown
- implement: true
- kind: ordinary

###### A.3.1[2].[t]*.[r][7] (Requirement Type)
- WordTraceId: 292773
- atomic: false
- Legal Obligation: not applicable
- implement: false
- kind: Table

###### A.3.1[2].[t]*.[r][7].Data (Requirement Type)
Value of MRSP where dV_ebi starts to increase to dV_ebi_max
- WordTraceId: 292773
- atomic: true
- Legal Obligation: unknown
- implement: true
- kind: ordinary

###### A.3.1[2].[t]*.[r][7].Value (Requirement Type)
110 km/h
- WordTraceId: 292833
- atomic: true
- Legal Obligation: unknown
- implement: true
- kind: ordinary

###### A.3.1[2].[t]*.[r][7].Name (Requirement Type)
V_ebi_min
- WordTraceId: 292842
- atomic: true
- Legal Obligation: unknown
- implement: true
- kind: ordinary

###### A.3.1[2].[t]*.[r][8] (Requirement Type)
- WordTraceId: 292853
- atomic: false
- Legal Obligation: not applicable
- implement: false
- kind: Table

###### A.3.1[2].[t]*.[r][8].Data (Requirement Type)
Value of MRSP where dV_ebi stops to increase to dV_ebi_max
- WordTraceId: 292853
- atomic: true
- Legal Obligation: unknown
- implement: true
- kind: ordinary

###### A.3.1[2].[t]*.[r][8].Value (Requirement Type)
210 km/h
- WordTraceId: 292912
- atomic: true
- Legal Obligation: unknown
- implement: true
- kind: ordinary

###### A.3.1[2].[t]*.[r][8].Name (Requirement Type)
V_ebi_max
- WordTraceId: 292921
- atomic: true
- Legal Obligation: unknown
- implement: true
- kind: ordinary

###### A.3.1[2].[t]*.[r][9] (Requirement Type)
- WordTraceId: 292932
- atomic: false
- Legal Obligation: not applicable
- implement: false
- kind: Table

###### A.3.1[2].[t]*.[r][9].Data (Requirement Type)
Speed difference between Permitted speed and Service Brake Intervention supervision limits, minimum value
- WordTraceId: 292932
- atomic: true
- Legal Obligation: unknown
- implement: true
- kind: ordinary

###### A.3.1[2].[t]*.[r][9].Value (Requirement Type)
5.5 km/h
- WordTraceId: 293038
- atomic: true
- Legal Obligation: unknown
- implement: true
- kind: ordinary

###### A.3.1[2].[t]*.[r][9].Name (Requirement Type)
dV_sbi_min
- WordTraceId: 293047
- atomic: true
- Legal Obligation: unknown
- implement: true
- kind: ordinary

###### A.3.1[2].[t]*.[r][10] (Requirement Type)
- WordTraceId: 293059
- atomic: false
- Legal Obligation: not applicable
- implement: false
- kind: Table

###### A.3.1[2].[t]*.[r][10].Data (Requirement Type)
Speed difference between Permitted speed and Service Brake Intervention supervision limits, maximum value
- WordTraceId: 293059
- atomic: true
- Legal Obligation: unknown
- implement: true
- kind: ordinary

###### A.3.1[2].[t]*.[r][10].Value (Requirement Type)
10 km/h
- WordTraceId: 293165
- atomic: true
- Legal Obligation: unknown
- implement: true
- kind: ordinary

###### A.3.1[2].[t]*.[r][10].Name (Requirement Type)
dV_sbi_max
- WordTraceId: 293173
- atomic: true
- Legal Obligation: unknown
- implement: true
- kind: ordinary

###### A.3.1[2].[t]*.[r][11] (Requirement Type)
- WordTraceId: 293185
- atomic: false
- Legal Obligation: not applicable
- implement: false
- kind: Table

###### A.3.1[2].[t]*.[r][11].Data (Requirement Type)
Value of MRSP where dV_sbi starts to increase to dV_sbi_max
- WordTraceId: 293185
- atomic: true
- Legal Obligation: unknown
- implement: true
- kind: ordinary

###### A.3.1[2].[t]*.[r][11].Value (Requirement Type)
110 km/h
- WordTraceId: 293245
- atomic: true
- Legal Obligation: unknown
- implement: true
- kind: ordinary

###### A.3.1[2].[t]*.[r][11].Name (Requirement Type)
V_sbi_min
- WordTraceId: 293254
- atomic: true
- Legal Obligation: unknown
- implement: true
- kind: ordinary

###### A.3.1[2].[t]*.[r][12] (Requirement Type)
- WordTraceId: 293265
- atomic: false
- Legal Obligation: not applicable
- implement: false
- kind: Table

###### A.3.1[2].[t]*.[r][12].Data (Requirement Type)
Value of MRSP where dV_sbi stops to increase to dV_sbi_max
- WordTraceId: 293265
- atomic: true
- Legal Obligation: unknown
- implement: true
- kind: ordinary

###### A.3.1[2].[t]*.[r][12].Value (Requirement Type)
210 km/h
- WordTraceId: 293324
- atomic: true
- Legal Obligation: unknown
- implement: true
- kind: ordinary

###### A.3.1[2].[t]*.[r][12].Name (Requirement Type)
V_sbi_max
- WordTraceId: 293333
- atomic: true
- Legal Obligation: unknown
- implement: true
- kind: ordinary

###### A.3.1[2].[t]*.[r][13] (Requirement Type)
- WordTraceId: 293344
- atomic: false
- Legal Obligation: not applicable
- implement: false
- kind: Table

###### A.3.1[2].[t]*.[r][13].Data (Requirement Type)
Speed difference between Permitted speed and Warning supervision limits, minimum value
- WordTraceId: 293344
- atomic: true
- Legal Obligation: unknown
- implement: true
- kind: ordinary

###### A.3.1[2].[t]*.[r][13].Value (Requirement Type)
4 km/h
- WordTraceId: 293431
- atomic: true
- Legal Obligation: unknown
- implement: true
- kind: ordinary

###### A.3.1[2].[t]*.[r][13].Name (Requirement Type)
dV_warning_min
- WordTraceId: 293438
- atomic: true
- Legal Obligation: unknown
- implement: true
- kind: ordinary

###### A.3.1[2].[t]*.[r][14] (Requirement Type)
- WordTraceId: 293454
- atomic: false
- Legal Obligation: not applicable
- implement: false
- kind: Table

###### A.3.1[2].[t]*.[r][14].Data (Requirement Type)
Speed difference between Permitted speed and Warning supervision limits, maximum value
- WordTraceId: 293454
- atomic: true
- Legal Obligation: unknown
- implement: true
- kind: ordinary

###### A.3.1[2].[t]*.[r][14].Value (Requirement Type)
5 km/h
- WordTraceId: 293541
- atomic: true
- Legal Obligation: unknown
- implement: true
- kind: ordinary

###### A.3.1[2].[t]*.[r][14].Name (Requirement Type)
dV_warning_max
- WordTraceId: 293548
- atomic: true
- Legal Obligation: unknown
- implement: true
- kind: ordinary

###### A.3.1[2].[t]*.[r][15] (Requirement Type)
- WordTraceId: 293564
- atomic: false
- Legal Obligation: not applicable
- implement: false
- kind: Table

###### A.3.1[2].[t]*.[r][15].Data (Requirement Type)
Value of MRSP where dV_warning starts to increase to dV_warning_max
- WordTraceId: 293564
- atomic: true
- Legal Obligation: unknown
- implement: true
- kind: ordinary

###### A.3.1[2].[t]*.[r][15].Value (Requirement Type)
110 km/h
- WordTraceId: 293632
- atomic: true
- Legal Obligation: unknown
- implement: true
- kind: ordinary

###### A.3.1[2].[t]*.[r][15].Name (Requirement Type)
V_warning_min
- WordTraceId: 293641
- atomic: true
- Legal Obligation: unknown
- implement: true
- kind: ordinary

###### A.3.1[2].[t]*.[r][16] (Requirement Type)
- WordTraceId: 293656
- atomic: false
- Legal Obligation: not applicable
- implement: false
- kind: Table

###### A.3.1[2].[t]*.[r][16].Data (Requirement Type)
Value of MRSP where dV_warning stops to increase to dV_warning_max
- WordTraceId: 293656
- atomic: true
- Legal Obligation: unknown
- implement: true
- kind: ordinary

###### A.3.1[2].[t]*.[r][16].Value (Requirement Type)
140 km/h
- WordTraceId: 293723
- atomic: true
- Legal Obligation: unknown
- implement: true
- kind: ordinary

###### A.3.1[2].[t]*.[r][16].Name (Requirement Type)
V_warning_max
- WordTraceId: 293732
- atomic: true
- Legal Obligation: unknown
- implement: true
- kind: ordinary

###### A.3.1[2].[t]*.[r][17] (Requirement Type)
- WordTraceId: 293747
- atomic: false
- Legal Obligation: not applicable
- implement: false
- kind: Table

###### A.3.1[2].[t]*.[r][17].Data (Requirement Type)
Time between Warning supervision limit and FLOI
- WordTraceId: 293747
- atomic: true
- Legal Obligation: unknown
- implement: true
- implementerEnhanced: Time
  [TIME]
  between Warning supervision limit and FLOI
- kind: ordinary

###### A.3.1[2].[t]*.[r][17].Value (Requirement Type)
2 s
- WordTraceId: 293795
- atomic: true
- Legal Obligation: unknown
- implement: true
- kind: ordinary

###### A.3.1[2].[t]*.[r][17].Name (Requirement Type)
T_warning
- WordTraceId: 293799
- atomic: true
- Legal Obligation: unknown
- implement: true
- kind: ordinary

###### A.3.1[2].[t]*.[r][18] (Requirement Type)
- WordTraceId: 293810
- atomic: false
- Legal Obligation: not applicable
- implement: false
- kind: Table

###### A.3.1[2].[t]*.[r][18].Data (Requirement Type)
Driver reaction time between Permitted speed supervision limit and FLOI
- WordTraceId: 293810
- atomic: true
- Legal Obligation: unknown
- implement: true
- implementerEnhanced: Driver
  [EXTERNAL]
  reaction
  time
  [TIME]
  between Permitted speed supervision limit and FLOI
- kind: ordinary

###### A.3.1[2].[t]*.[r][18].Value (Requirement Type)
4 s
- WordTraceId: 293882
- atomic: true
- Legal Obligation: unknown
- implement: true
- kind: ordinary

###### A.3.1[2].[t]*.[r][18].Name (Requirement Type)
T_driver
- WordTraceId: 293886
- atomic: true
- Legal Obligation: unknown
- implement: true
- kind: ordinary

###### A.3.1[2].[t]*.[r][19] (Requirement Type)
- WordTraceId: 293896
- atomic: false
- Legal Obligation: not applicable
- implement: false
- kind: Table

###### A.3.1[2].[t]*.[r][19].Data (Requirement Type)
Time between the pre-indication location and the indication supervision limit valid for MRSP speed.
- WordTraceId: 293896
- atomic: true
- Legal Obligation: unknown
- implement: true
- implementerEnhanced: Time
  [TIME]
  between the pre-indication location and the indication supervision limit valid for MRSP speed.
- kind: ordinary

###### A.3.1[2].[t]*.[r][19].Value (Requirement Type)
7 s
- WordTraceId: 293996
- atomic: true
- Legal Obligation: unknown
- implement: true
- kind: ordinary

###### A.3.1[2].[t]*.[r][19].Name (Requirement Type)
T_preindication
- WordTraceId: 294000
- atomic: true
- Legal Obligation: unknown
- implement: true
- kind: ordinary

###### A.3.1[2].[t]*.[r][20] (Requirement Type)
- WordTraceId: 294017
- atomic: false
- Legal Obligation: not applicable
- implement: false
- kind: Table

###### A.3.1[2].[t]*.[r][20].Data (Requirement Type)
Maximum possible rotating mass as a percentage of the total weight of the train
- WordTraceId: 294017
- atomic: true
- Legal Obligation: unknown
- implement: true
- kind: ordinary

###### A.3.1[2].[t]*.[r][20].Value (Requirement Type)
15 %
- WordTraceId: 294097
- atomic: true
- Legal Obligation: unknown
- implement: true
- kind: ordinary

###### A.3.1[2].[t]*.[r][20].Name (Requirement Type)
M_rotating_max
- WordTraceId: 294102
- atomic: true
- Legal Obligation: unknown
- implement: true
- kind: ordinary

###### A.3.1[2].[t]*.[r][21] (Requirement Type)
- WordTraceId: 294118
- atomic: false
- Legal Obligation: not applicable
- implement: false
- kind: Table

###### A.3.1[2].[t]*.[r][21].Data (Requirement Type)
Minimum possible rotating mass as a percentage of the total weight of the train
- WordTraceId: 294118
- atomic: true
- Legal Obligation: unknown
- implement: true
- kind: ordinary

###### A.3.1[2].[t]*.[r][21].Value (Requirement Type)
2 %
- WordTraceId: 294198
- atomic: true
- Legal Obligation: unknown
- implement: true
- kind: ordinary

###### A.3.1[2].[t]*.[r][21].Name (Requirement Type)
M_rotating_min
- WordTraceId: 294202
- atomic: true
- Legal Obligation: unknown
- implement: true
- kind: ordinary

###### A.3.1[2].[t]*.[r][22] (Requirement Type)
- WordTraceId: 294218
- atomic: false
- Legal Obligation: not applicable
- implement: false
- kind: Table

###### A.3.1[2].[t]*.[r][22].Data (Requirement Type)
Compensation of the speed measurement inaccuracy used for the calculation of speed restriction to ensure given permitted braking distance
- WordTraceId: 294218
- atomic: true
- Legal Obligation: unknown
- implement: true
- kind: ordinary

###### A.3.1[2].[t]*.[r][22].Value (Requirement Type)
5 km/h
- WordTraceId: 294356
- atomic: true
- Legal Obligation: unknown
- implement: true
- kind: ordinary

###### A.3.1[2].[t]*.[r][22].Name (Requirement Type)
- WordTraceId: 294363
- atomic: true
- Legal Obligation: unknown
- implement: true
- kind: ordinary

###### A.3.1[2].[t]*.[r][23] (Requirement Type)
- WordTraceId: 294365
- atomic: false
- Legal Obligation: not applicable
- implement: false
- kind: Table

###### A.3.1[2].[t]*.[r][23].Data (Requirement Type)
MA request repetition cycle, default value
- WordTraceId: 294365
- atomic: true
- Legal Obligation: unknown
- implement: true
- implementerEnhanced: MA request
  repetition
  [LOOP]
  cycle, default value
- kind: ordinary

###### A.3.1[2].[t]*.[r][23].Value (Requirement Type)
60 s
- WordTraceId: 294408
- atomic: true
- Legal Obligation: unknown
- implement: true
- kind: ordinary

###### A.3.1[2].[t]*.[r][23].Name (Requirement Type)
T CYCRQSTD
- WordTraceId: 294413
- atomic: true
- Legal Obligation: unknown
- PlainText: TCYCRQSTD
- implement: true
- implementerEnhanced: TCYCRQSTD
- kind: ordinary

###### A.3.1[2].[t]*.[r][24] (Requirement Type)
- WordTraceId: 294424
- atomic: false
- Legal Obligation: not applicable
- implement: false
- kind: Table

###### A.3.1[2].[t]*.[r][24].Data (Requirement Type)
Mode transitions:
Driver acknowledgement time
- WordTraceId: 294424
- atomic: true
- Legal Obligation: unknown
- implement: true
- implementerEnhanced: Mode transitions:
  Driver
  [EXTERNAL]
  acknowledgement
  time
  [TIME]
- kind: ordinary

###### A.3.1[2].[t]*.[r][24].Value (Requirement Type)
5 s
- WordTraceId: 294470
- atomic: true
- Legal Obligation: unknown
- implement: true
- kind: ordinary

###### A.3.1[2].[t]*.[r][24].Name (Requirement Type)
T ACK
- WordTraceId: 294474
- atomic: true
- Legal Obligation: unknown
- PlainText: TACK
- implement: true
- implementerEnhanced: TACK
- kind: ordinary

###### A.3.1[2].[t]*.[r][25] (Requirement Type)
- WordTraceId: 294480
- atomic: false
- Legal Obligation: not applicable
- implement: false
- kind: Table

###### A.3.1[2].[t]*.[r][25].Data (Requirement Type)
Maximum time to maintain a communication session in case of failed re-connection attempts
- WordTraceId: 294480
- atomic: true
- Legal Obligation: unknown
- implement: true
- implementerEnhanced: Maximum
  time
  [TIME]
  to maintain a communication session
  in case of
  [CONDITION]
  failed
  re-connection
  [AGAIN]
  attempts
- kind: ordinary

###### A.3.1[2].[t]*.[r][25].Value (Requirement Type)
5 minutes
- WordTraceId: 294570
- atomic: true
- Legal Obligation: unknown
- implement: true
- kind: ordinary

###### A.3.1[2].[t]*.[r][25].Name (Requirement Type)
- WordTraceId: 294580
- atomic: true
- Legal Obligation: unknown
- implement: true
- kind: ordinary

###### A.3.1[2].[t]*.[r][26] (Requirement Type)
- WordTraceId: 294582
- atomic: false
- Legal Obligation: not applicable
- implement: false
- kind: Table

###### A.3.1[2].[t]*.[r][26].Data (Requirement Type)
Distance of metal immunity in Levels 0/NTC
- WordTraceId: 294582
- atomic: true
- Legal Obligation: unknown
- implement: true
- kind: ordinary

###### A.3.1[2].[t]*.[r][26].Value (Requirement Type)
300 metres
- WordTraceId: 294625
- atomic: true
- Legal Obligation: unknown
- implement: true
- kind: ordinary

###### A.3.1[2].[t]*.[r][26].Name (Requirement Type)
D_Metal
- WordTraceId: 294636
- atomic: true
- Legal Obligation: unknown
- implement: true
- kind: ordinary

###### A.3.1[2].[t]*.[r][27] (Requirement Type)
- WordTraceId: 294645
- atomic: false
- Legal Obligation: not applicable
- implement: false
- kind: Table

###### A.3.1[2].[t]*.[r][27].Data (Requirement Type)
Driver reaction time before sounding the horn
- WordTraceId: 294645
- atomic: true
- Legal Obligation: unknown
- implement: true
- implementerEnhanced: Driver
  [EXTERNAL]
  reaction
  time
  [TIME]
  before sounding the horn
- kind: ordinary

###### A.3.1[2].[t]*.[r][27].Value (Requirement Type)
4 s
- WordTraceId: 294691
- atomic: true
- Legal Obligation: unknown
- implement: true
- kind: ordinary

###### A.3.1[2].[t]*.[r][27].Name (Requirement Type)
- WordTraceId: 294695
- atomic: true
- Legal Obligation: unknown
- implement: true
- kind: ordinary

###### A.3.1[2].[t]*.[r][28] (Requirement Type)
- WordTraceId: 294697
- atomic: false
- Legal Obligation: not applicable
- implement: false
- kind: Table

###### A.3.1[2].[t]*.[r][28].Data (Requirement Type)
Time between minimum safe rear end of the train leaving a track condition area and on-board deleting the applicable indication
- WordTraceId: 294697
- atomic: true
- Legal Obligation: unknown
- implement: true
- implementerEnhanced: Time
  [TIME]
  between minimum safe rear end of the train leaving a track condition area and on-board deleting the applicable indication
- kind: ordinary

###### A.3.1[2].[t]*.[r][28].Value (Requirement Type)
5 s
- WordTraceId: 294824
- atomic: true
- Legal Obligation: unknown
- implement: true
- kind: ordinary

###### A.3.1[2].[t]*.[r][28].Name (Requirement Type)
- WordTraceId: 294828
- atomic: true
- Legal Obligation: unknown
- implement: true
- kind: ordinary

###### A.3.1[2].[t]*.[r][29] (Requirement Type)
- WordTraceId: 294830
- atomic: false
- Legal Obligation: not applicable
- implement: false
- kind: Table

###### A.3.1[2].[t]*.[r][29].Data (Requirement Type)
Distance to keep on-board information in rear of the min safe rear end of the train
- WordTraceId: 294830
- atomic: true
- Legal Obligation: unknown
- implement: true
- kind: ordinary

###### A.3.1[2].[t]*.[r][29].Value (Requirement Type)
300 metres
- WordTraceId: 294914
- atomic: true
- Legal Obligation: unknown
- implement: true
- kind: ordinary

###### A.3.1[2].[t]*.[r][29].Name (Requirement Type)
- WordTraceId: 294925
- atomic: true
- Legal Obligation: unknown
- implement: true
- kind: ordinary

###### A.3.1[2].[t]*.[r][30] (Requirement Type)
- WordTraceId: 294927
- atomic: false
- Legal Obligation: not applicable
- implement: false
- kind: Table

###### A.3.1[2].[t]*.[r][30].Data (Requirement Type)
Additional delay time to disconnection on supervision of safe radio connection
- WordTraceId: 294927
- atomic: true
- Legal Obligation: unknown
- implement: true
- implementerEnhanced: Additional
  delay
  [TIME]
  time
  [TIME]
  to disconnection on supervision of safe radio connection
- kind: ordinary

###### A.3.1[2].[t]*.[r][30].Value (Requirement Type)
60 s
- WordTraceId: 295006
- atomic: true
- Legal Obligation: unknown
- implement: true
- kind: ordinary

###### A.3.1[2].[t]*.[r][30].Name (Requirement Type)
- WordTraceId: 295011
- atomic: true
- Legal Obligation: unknown
- implement: true
- kind: ordinary

###### A.3.1[2].[t]*.[r][31] (Requirement Type)
- WordTraceId: 295013
- atomic: false
- Legal Obligation: not applicable
- implement: false
- kind: Table

###### A.3.1[2].[t]*.[r][31].Data (Requirement Type)
“Connection status” timer for safe radio connection indication
- WordTraceId: 295013
- atomic: true
- Legal Obligation: unknown
- implement: true
- implementerEnhanced: “
  Connection status
  [LINKED_PHRASE]
  ”
  timer
  [TIME]
  for safe radio connection indication
- kind: ordinary
- KnownTermLink -> 3.5.7.2

###### A.3.1[2].[t]*.[r][31].Value (Requirement Type)
45 s
- WordTraceId: 295076
- atomic: true
- Legal Obligation: unknown
- implement: true
- kind: ordinary

###### A.3.1[2].[t]*.[r][31].Name (Requirement Type)
- WordTraceId: 295081
- atomic: true
- Legal Obligation: unknown
- implement: true
- kind: ordinary

#### A.3.2 (Requirement Type)
A.3.2 List of National / Default Data
- WordTraceId: 295084
- atomic: false
- Legal Obligation: not applicable
- PlainText: List of National / Default Data
- implement: true
- implementerEnhanced: List of National / Default Data
- kind: ordinary

#### A.3.2[2] (Requirement Type)
- WordTraceId: 295123
- atomic: false
- Legal Obligation: not applicable
- implement: false
- kind: Placeholder

##### A.3.2[2].[t]* (Requirement Type)
| National / Default Data | Default Value | SRS Name (Reference only) |
| --- | --- | --- |
| [r][2].Data Modification of adhesion factor by driver | [r][2].Value Not allowed | [r][2].Name Q_NVDRIVER_ADHES |
| [r][3].Data Shunting mode speed limit | [r][3].Value 30km/h | [r][3].Name V_NVSHUNT |
| [r][4].Data Staff Responsible mode speed limit | [r][4].Value 40km/h | [r][4].Name V_NVSTFF |
| [r][5].Data On Sight mode speed limit | [r][5].Value 30km/h | [r][5].Name V_NVONSIGHT |
| [r][6].Data Limited Supervision mode speed limit | [r][6].Value 100 km/h | [r][6].Name V_NVLIMSUPERV |
| [r][7].Data Unfitted mode speed limit | [r][7].Value 100km/h | [r][7].Name V_NVUNFIT |
| [r][8].Data Release Speed | [r][8].Value 40km/h | [r][8].Name V_NVREL |
| [r][9].Data Distance to be used in Roll Away protection, Reverse movement protection and Standstill supervision | [r][9].Value 2m | [r][9].Name D_NVROLL |
| [r][10].Data Permission to use service brake in target speed monitoring | [r][10].Value Yes | [r][10].Name Q_NVSBTSMPERM |
| [r][11].Data Permission to release emergency brake | [r][11].Value Only at standstill | [r][11].Name Q_NVEMRRLS |
| [r][12].Data Permission to use guidance curves | [r][12].Value No | [r][12].Name Q_NVGUIPERM |
| [r][13].Data Permission to use the service brake feedback | [r][13].Value No | [r][13].Name Q_NVSBFBPERM |
| [r][14].Data Permission to inhibit the compensation of the speed measurement inaccuracy | [r][14].Value No | [r][14].Name Q_NVINHSMICPERM |
| [r][15].Data Speed limit for triggering the override function | [r][15].Value 0km/h | [r][15].Name V_NVALLOWOVTRP |
| [r][16].Data Override speed limit to be supervised when the “override” function is active | [r][16].Value 30 km/h | [r][16].Name V_NVSUPOVTRP |
| [r][17].Data Distance for train trip suppression when override function is triggered | [r][17].Value 200m | [r][17].Name D_NVOVTRP |
| [r][18].Data Max. time for train trip suppression when override function is triggered | [r][18].Value 60 s | [r][18].Name T_NVOVTRP |
| [r][19].Data Change of driver ID permitted while running | [r][19].Value Yes | [r][19].Name M_NVDERUN |
| [r][20].Data System reaction if radio channel monitoring time limit expires (T-Contact) | [r][20].Value No reaction | [r][20].Name M_NVCONTACT |
| [r][21].Data Maximum time since creation in the RBC of last received telegram. | [r][21].Value ∞ | [r][21].Name T_NVCONTACT |
| [r][22].Data Distance to be allowed for reversing in Post Trip mode. | [r][22].Value 200 m | [r][22].Name D_NVPOTRP |
| [r][23].Data Max permitted distance to run in Staff Responsible mode | [r][23].Value ∞ | [r][23].Name D_NVSTFF |
| [r][24].Data Default location accuracy of a balise group | [r][24].Value 12 m | [r][24].Name Q_NVLOCACC |
| [r][25].Data Weighting factor for available wheel/rail adhesion | [r][25].Value 0 | [r][25].Name M_NVAVADH |
| [r][26].Data Confidence level for emergency brake safe deceleration on dry rails | [r][26].Value 99.9999999 % | [r][26].Name M_NVEBCL |
| [r][27].Data Train length step used for the integrated correction factor Kr_int | [r][27].Value N/A | [r][27].Name L_NVKRINT |
| [r][28].Data Train length dependent integrated correction factor Kr_int | [r][28].Value 0.9 | [r][28].Name M_NVKRINT* |
| [r][29].Data Speed step used for the integrated correction factor Kv_int | [r][29].Value N/A | [r][29].Name V_NVKVINT |
| [r][30].Data Speed dependent integrated correction factor Kv_int | [r][30].Value 0.7 | [r][30].Name M_NVKVINT* |
| [r][31].Data Integrated correction factor for brake build up time | [r][31].Value 1.1 | [r][31].Name M_NVKTINT |
| [r][32].Data Maximum deceleration value under reduced adhesion conditions (1) | [r][32].Value 1.0 m/s 2 | [r][32].Name A_NVMAXREDADH1 |
| [r][33].Data Maximum deceleration value under reduced adhesion conditions (2) | [r][33].Value 0.7 m/s 2 | [r][33].Name A_NVMAXREDADH2 |
| [r][34].Data Maximum deceleration value under reduced adhesion conditions (3) | [r][34].Value 0.7 m/s 2 | [r][34].Name A_NVMAXREDADH3 |
| [r][35].Data Lower deceleration limit to determine the set of Kv_int to be used | [r][35].Value N/A | [r][35].Name A_NVP12 |
| [r][36].Data Upper deceleration limit to determine the set of Kv_int to be used | [r][36].Value N/A | [r][36].Name A_NVP23 |
- WordTraceId: 297750
- atomic: false
- Legal Obligation: not applicable
- implement: false
- kind: Table

###### A.3.2[2].[t]*.[r][2] (Requirement Type)
- WordTraceId: 295188
- atomic: false
- Legal Obligation: not applicable
- implement: false
- kind: Table

###### A.3.2[2].[t]*.[r][2].Data (Requirement Type)
Modification of adhesion factor by driver
- WordTraceId: 295188
- atomic: true
- Legal Obligation: unknown
- implement: true
- implementerEnhanced: Modification of adhesion factor by
  driver
  [EXTERNAL]
- kind: ordinary

###### A.3.2[2].[t]*.[r][2].Value (Requirement Type)
Not allowed
- WordTraceId: 295230
- atomic: true
- Legal Obligation: unknown
- implement: true
- kind: ordinary

###### A.3.2[2].[t]*.[r][2].Name (Requirement Type)
Q_NVDRIVER_ADHES
- WordTraceId: 295242
- atomic: true
- Legal Obligation: unknown
- implement: true
- kind: ordinary

###### A.3.2[2].[t]*.[r][3] (Requirement Type)
- WordTraceId: 295260
- atomic: false
- Legal Obligation: not applicable
- implement: false
- kind: Table

###### A.3.2[2].[t]*.[r][3].Data (Requirement Type)
Shunting mode speed limit
- WordTraceId: 295260
- atomic: true
- Legal Obligation: unknown
- implement: true
- kind: ordinary

###### A.3.2[2].[t]*.[r][3].Value (Requirement Type)
30km/h
- WordTraceId: 295286
- atomic: true
- Legal Obligation: unknown
- implement: true
- kind: ordinary

###### A.3.2[2].[t]*.[r][3].Name (Requirement Type)
V_NVSHUNT
- WordTraceId: 295293
- atomic: true
- Legal Obligation: unknown
- implement: true
- kind: ordinary

###### A.3.2[2].[t]*.[r][4] (Requirement Type)
- WordTraceId: 295304
- atomic: false
- Legal Obligation: not applicable
- implement: false
- kind: Table

###### A.3.2[2].[t]*.[r][4].Data (Requirement Type)
Staff Responsible mode speed limit
- WordTraceId: 295304
- atomic: true
- Legal Obligation: unknown
- implement: true
- kind: ordinary

###### A.3.2[2].[t]*.[r][4].Value (Requirement Type)
40km/h
- WordTraceId: 295339
- atomic: true
- Legal Obligation: unknown
- implement: true
- kind: ordinary

###### A.3.2[2].[t]*.[r][4].Name (Requirement Type)
V_NVSTFF
- WordTraceId: 295346
- atomic: true
- Legal Obligation: unknown
- implement: true
- kind: ordinary

###### A.3.2[2].[t]*.[r][5] (Requirement Type)
- WordTraceId: 295356
- atomic: false
- Legal Obligation: not applicable
- implement: false
- kind: Table

###### A.3.2[2].[t]*.[r][5].Data (Requirement Type)
On Sight mode speed limit
- WordTraceId: 295356
- atomic: true
- Legal Obligation: unknown
- implement: true
- kind: ordinary

###### A.3.2[2].[t]*.[r][5].Value (Requirement Type)
30km/h
- WordTraceId: 295382
- atomic: true
- Legal Obligation: unknown
- implement: true
- kind: ordinary

###### A.3.2[2].[t]*.[r][5].Name (Requirement Type)
V_NVONSIGHT
- WordTraceId: 295389
- atomic: true
- Legal Obligation: unknown
- implement: true
- kind: ordinary

###### A.3.2[2].[t]*.[r][6] (Requirement Type)
- WordTraceId: 295402
- atomic: false
- Legal Obligation: not applicable
- implement: false
- kind: Table

###### A.3.2[2].[t]*.[r][6].Data (Requirement Type)
Limited Supervision mode speed limit
- WordTraceId: 295402
- atomic: true
- Legal Obligation: unknown
- implement: true
- kind: ordinary

###### A.3.2[2].[t]*.[r][6].Value (Requirement Type)
100 km/h
- WordTraceId: 295439
- atomic: true
- Legal Obligation: unknown
- implement: true
- kind: ordinary

###### A.3.2[2].[t]*.[r][6].Name (Requirement Type)
V_NVLIMSUPERV
- WordTraceId: 295448
- atomic: true
- Legal Obligation: unknown
- implement: true
- kind: ordinary

###### A.3.2[2].[t]*.[r][7] (Requirement Type)
- WordTraceId: 295463
- atomic: false
- Legal Obligation: not applicable
- implement: false
- kind: Table

###### A.3.2[2].[t]*.[r][7].Data (Requirement Type)
Unfitted mode speed limit
- WordTraceId: 295463
- atomic: true
- Legal Obligation: unknown
- implement: true
- kind: ordinary

###### A.3.2[2].[t]*.[r][7].Value (Requirement Type)
100km/h
- WordTraceId: 295489
- atomic: true
- Legal Obligation: unknown
- implement: true
- kind: ordinary

###### A.3.2[2].[t]*.[r][7].Name (Requirement Type)
V_NVUNFIT
- WordTraceId: 295497
- atomic: true
- Legal Obligation: unknown
- implement: true
- kind: ordinary

###### A.3.2[2].[t]*.[r][8] (Requirement Type)
- WordTraceId: 295508
- atomic: false
- Legal Obligation: not applicable
- implement: false
- kind: Table

###### A.3.2[2].[t]*.[r][8].Data (Requirement Type)
Release Speed
- WordTraceId: 295508
- atomic: true
- Legal Obligation: unknown
- implement: true
- kind: ordinary

###### A.3.2[2].[t]*.[r][8].Value (Requirement Type)
40km/h
- WordTraceId: 295522
- atomic: true
- Legal Obligation: unknown
- implement: true
- kind: ordinary

###### A.3.2[2].[t]*.[r][8].Name (Requirement Type)
V_NVREL
- WordTraceId: 295529
- atomic: true
- Legal Obligation: unknown
- implement: true
- kind: ordinary

###### A.3.2[2].[t]*.[r][9] (Requirement Type)
- WordTraceId: 295538
- atomic: false
- Legal Obligation: not applicable
- implement: false
- kind: Table

###### A.3.2[2].[t]*.[r][9].Data (Requirement Type)
Distance to be used in Roll Away protection, Reverse movement protection and Standstill supervision
- WordTraceId: 295538
- atomic: true
- Legal Obligation: unknown
- implement: true
- kind: ordinary

###### A.3.2[2].[t]*.[r][9].Value (Requirement Type)
2m
- WordTraceId: 295638
- atomic: true
- Legal Obligation: unknown
- implement: true
- kind: ordinary

###### A.3.2[2].[t]*.[r][9].Name (Requirement Type)
D_NVROLL
- WordTraceId: 295641
- atomic: true
- Legal Obligation: unknown
- implement: true
- kind: ordinary

###### A.3.2[2].[t]*.[r][10] (Requirement Type)
- WordTraceId: 295651
- atomic: false
- Legal Obligation: not applicable
- implement: false
- kind: Table

###### A.3.2[2].[t]*.[r][10].Data (Requirement Type)
Permission to use service brake in target speed monitoring
- WordTraceId: 295651
- atomic: true
- Legal Obligation: unknown
- implement: true
- kind: ordinary

###### A.3.2[2].[t]*.[r][10].Value (Requirement Type)
Yes
- WordTraceId: 295710
- atomic: true
- Legal Obligation: unknown
- implement: true
- kind: ordinary

###### A.3.2[2].[t]*.[r][10].Name (Requirement Type)
Q_NVSBTSMPERM
- WordTraceId: 295714
- atomic: true
- Legal Obligation: unknown
- implement: true
- kind: ordinary

###### A.3.2[2].[t]*.[r][11] (Requirement Type)
- WordTraceId: 295729
- atomic: false
- Legal Obligation: not applicable
- implement: false
- kind: Table

###### A.3.2[2].[t]*.[r][11].Data (Requirement Type)
Permission to release emergency brake
- WordTraceId: 295729
- atomic: true
- Legal Obligation: unknown
- implement: true
- kind: ordinary

###### A.3.2[2].[t]*.[r][11].Value (Requirement Type)
Only at standstill
- WordTraceId: 295767
- atomic: true
- Legal Obligation: unknown
- implement: true
- kind: ordinary

###### A.3.2[2].[t]*.[r][11].Name (Requirement Type)
Q_NVEMRRLS
- WordTraceId: 295786
- atomic: true
- Legal Obligation: unknown
- implement: true
- kind: ordinary

###### A.3.2[2].[t]*.[r][12] (Requirement Type)
- WordTraceId: 295798
- atomic: false
- Legal Obligation: not applicable
- implement: false
- kind: Table

###### A.3.2[2].[t]*.[r][12].Data (Requirement Type)
Permission to use guidance curves
- WordTraceId: 295798
- atomic: true
- Legal Obligation: unknown
- implement: true
- kind: ordinary

###### A.3.2[2].[t]*.[r][12].Value (Requirement Type)
No
- WordTraceId: 295832
- atomic: true
- Legal Obligation: unknown
- implement: true
- kind: ordinary

###### A.3.2[2].[t]*.[r][12].Name (Requirement Type)
Q_NVGUIPERM
- WordTraceId: 295835
- atomic: true
- Legal Obligation: unknown
- implement: true
- kind: ordinary

###### A.3.2[2].[t]*.[r][13] (Requirement Type)
- WordTraceId: 295848
- atomic: false
- Legal Obligation: not applicable
- implement: false
- kind: Table

###### A.3.2[2].[t]*.[r][13].Data (Requirement Type)
Permission to use the service brake feedback
- WordTraceId: 295848
- atomic: true
- Legal Obligation: unknown
- implement: true
- kind: ordinary

###### A.3.2[2].[t]*.[r][13].Value (Requirement Type)
No
- WordTraceId: 295893
- atomic: true
- Legal Obligation: unknown
- implement: true
- kind: ordinary

###### A.3.2[2].[t]*.[r][13].Name (Requirement Type)
Q_NVSBFBPERM
- WordTraceId: 295896
- atomic: true
- Legal Obligation: unknown
- implement: true
- kind: ordinary

###### A.3.2[2].[t]*.[r][14] (Requirement Type)
- WordTraceId: 295910
- atomic: false
- Legal Obligation: not applicable
- implement: false
- kind: Table

###### A.3.2[2].[t]*.[r][14].Data (Requirement Type)
Permission to inhibit the compensation of the speed measurement inaccuracy
- WordTraceId: 295910
- atomic: true
- Legal Obligation: unknown
- implement: true
- kind: ordinary

###### A.3.2[2].[t]*.[r][14].Value (Requirement Type)
No
- WordTraceId: 295985
- atomic: true
- Legal Obligation: unknown
- implement: true
- kind: ordinary

###### A.3.2[2].[t]*.[r][14].Name (Requirement Type)
Q_NVINHSMICPERM
- WordTraceId: 295988
- atomic: true
- Legal Obligation: unknown
- implement: true
- kind: ordinary

###### A.3.2[2].[t]*.[r][15] (Requirement Type)
- WordTraceId: 296005
- atomic: false
- Legal Obligation: not applicable
- implement: false
- kind: Table

###### A.3.2[2].[t]*.[r][15].Data (Requirement Type)
Speed limit for triggering the override function
- WordTraceId: 296005
- atomic: true
- Legal Obligation: unknown
- implement: true
- kind: ordinary

###### A.3.2[2].[t]*.[r][15].Value (Requirement Type)
0km/h
- WordTraceId: 296054
- atomic: true
- Legal Obligation: unknown
- implement: true
- kind: ordinary

###### A.3.2[2].[t]*.[r][15].Name (Requirement Type)
V_NVALLOWOVTRP
- WordTraceId: 296060
- atomic: true
- Legal Obligation: unknown
- implement: true
- kind: ordinary

###### A.3.2[2].[t]*.[r][16] (Requirement Type)
- WordTraceId: 296077
- atomic: false
- Legal Obligation: not applicable
- implement: false
- kind: Table

###### A.3.2[2].[t]*.[r][16].Data (Requirement Type)
Override speed limit to be supervised when the “override” function is active
- WordTraceId: 296077
- atomic: true
- Legal Obligation: unknown
- implement: true
- implementerEnhanced: Override speed limit to be supervised
  when
  [CONDITION]
  the “override” function is active
- kind: ordinary

###### A.3.2[2].[t]*.[r][16].Value (Requirement Type)
30 km/h
- WordTraceId: 296155
- atomic: true
- Legal Obligation: unknown
- implement: true
- kind: ordinary

###### A.3.2[2].[t]*.[r][16].Name (Requirement Type)
V_NVSUPOVTRP
- WordTraceId: 296163
- atomic: true
- Legal Obligation: unknown
- implement: true
- kind: ordinary

###### A.3.2[2].[t]*.[r][17] (Requirement Type)
- WordTraceId: 296178
- atomic: false
- Legal Obligation: not applicable
- implement: false
- kind: Table

###### A.3.2[2].[t]*.[r][17].Data (Requirement Type)
Distance for train trip suppression when override function is triggered
- WordTraceId: 296178
- atomic: true
- Legal Obligation: unknown
- implement: true
- implementerEnhanced: Distance for train trip suppression
  when
  [CONDITION]
  override function is triggered
- kind: ordinary

###### A.3.2[2].[t]*.[r][17].Value (Requirement Type)
200m
- WordTraceId: 296250
- atomic: true
- Legal Obligation: unknown
- implement: true
- kind: ordinary

###### A.3.2[2].[t]*.[r][17].Name (Requirement Type)
D_NVOVTRP
- WordTraceId: 296255
- atomic: true
- Legal Obligation: unknown
- implement: true
- kind: ordinary

###### A.3.2[2].[t]*.[r][18] (Requirement Type)
- WordTraceId: 296266
- atomic: false
- Legal Obligation: not applicable
- implement: false
- kind: Table

###### A.3.2[2].[t]*.[r][18].Data (Requirement Type)
Max. time for train trip suppression when override function is triggered
- WordTraceId: 296266
- atomic: true
- Legal Obligation: unknown
- implement: true
- implementerEnhanced: Max.
  time
  [TIME]
  for train trip suppression
  when
  [CONDITION]
  override function is triggered
- kind: ordinary

###### A.3.2[2].[t]*.[r][18].Value (Requirement Type)
60 s
- WordTraceId: 296339
- atomic: true
- Legal Obligation: unknown
- implement: true
- kind: ordinary

###### A.3.2[2].[t]*.[r][18].Name (Requirement Type)
T_NVOVTRP
- WordTraceId: 296344
- atomic: true
- Legal Obligation: unknown
- implement: true
- kind: ordinary

###### A.3.2[2].[t]*.[r][19] (Requirement Type)
- WordTraceId: 296355
- atomic: false
- Legal Obligation: not applicable
- implement: false
- kind: Table

###### A.3.2[2].[t]*.[r][19].Data (Requirement Type)
Change of driver ID permitted while running
- WordTraceId: 296355
- atomic: true
- Legal Obligation: unknown
- implement: true
- implementerEnhanced: Change of driver ID permitted
  while
  [TIME]
  running
- kind: ordinary

###### A.3.2[2].[t]*.[r][19].Value (Requirement Type)
Yes
- WordTraceId: 296399
- atomic: true
- Legal Obligation: unknown
- implement: true
- kind: ordinary

###### A.3.2[2].[t]*.[r][19].Name (Requirement Type)
M_NVDERUN
- WordTraceId: 296403
- atomic: true
- Legal Obligation: unknown
- implement: true
- kind: ordinary

###### A.3.2[2].[t]*.[r][20] (Requirement Type)
- WordTraceId: 296414
- atomic: false
- Legal Obligation: not applicable
- implement: false
- kind: Table

###### A.3.2[2].[t]*.[r][20].Data (Requirement Type)
System reaction if radio channel monitoring time limit expires (T-Contact)
- WordTraceId: 296414
- atomic: true
- Legal Obligation: unknown
- implement: true
- implementerEnhanced: System reaction
  if
  [CONDITION]
  radio channel monitoring
  time
  [TIME]
  limit expires (T-Contact)
- kind: ordinary

###### A.3.2[2].[t]*.[r][20].Value (Requirement Type)
No reaction
- WordTraceId: 296489
- atomic: true
- Legal Obligation: unknown
- implement: true
- kind: ordinary

###### A.3.2[2].[t]*.[r][20].Name (Requirement Type)
M_NVCONTACT
- WordTraceId: 296501
- atomic: true
- Legal Obligation: unknown
- implement: true
- kind: ordinary

###### A.3.2[2].[t]*.[r][21] (Requirement Type)
- WordTraceId: 296514
- atomic: false
- Legal Obligation: not applicable
- implement: false
- kind: Table

###### A.3.2[2].[t]*.[r][21].Data (Requirement Type)
Maximum time since creation in the RBC of last received telegram.
- WordTraceId: 296514
- atomic: true
- Legal Obligation: unknown
- implement: true
- implementerEnhanced: Maximum
  time
  [TIME]
  since creation in the
  RBC
  [EXTERNAL]
  of last received telegram.
- kind: ordinary

###### A.3.2[2].[t]*.[r][21].Value (Requirement Type)
∞
- WordTraceId: 296580
- atomic: true
- Legal Obligation: unknown
- implement: true
- kind: ordinary

###### A.3.2[2].[t]*.[r][21].Name (Requirement Type)
T_NVCONTACT
- WordTraceId: 296582
- atomic: true
- Legal Obligation: unknown
- implement: true
- kind: ordinary

###### A.3.2[2].[t]*.[r][22] (Requirement Type)
- WordTraceId: 296595
- atomic: false
- Legal Obligation: not applicable
- implement: false
- kind: Table

###### A.3.2[2].[t]*.[r][22].Data (Requirement Type)
Distance to be allowed for reversing in Post Trip mode.
- WordTraceId: 296595
- atomic: true
- Legal Obligation: unknown
- implement: true
- kind: ordinary

###### A.3.2[2].[t]*.[r][22].Value (Requirement Type)
200 m
- WordTraceId: 296651
- atomic: true
- Legal Obligation: unknown
- implement: true
- kind: ordinary

###### A.3.2[2].[t]*.[r][22].Name (Requirement Type)
D_NVPOTRP
- WordTraceId: 296657
- atomic: true
- Legal Obligation: unknown
- implement: true
- kind: ordinary

###### A.3.2[2].[t]*.[r][23] (Requirement Type)
- WordTraceId: 296668
- atomic: false
- Legal Obligation: not applicable
- implement: false
- kind: Table

###### A.3.2[2].[t]*.[r][23].Data (Requirement Type)
Max permitted distance to run in Staff Responsible mode
- WordTraceId: 296668
- atomic: true
- Legal Obligation: unknown
- implement: true
- kind: ordinary

###### A.3.2[2].[t]*.[r][23].Value (Requirement Type)
∞
- WordTraceId: 296724
- atomic: true
- Legal Obligation: unknown
- implement: true
- kind: ordinary

###### A.3.2[2].[t]*.[r][23].Name (Requirement Type)
D_NVSTFF
- WordTraceId: 296726
- atomic: true
- Legal Obligation: unknown
- implement: true
- kind: ordinary

###### A.3.2[2].[t]*.[r][24] (Requirement Type)
- WordTraceId: 296736
- atomic: false
- Legal Obligation: not applicable
- implement: false
- kind: Table

###### A.3.2[2].[t]*.[r][24].Data (Requirement Type)
Default location accuracy of a balise group
- WordTraceId: 296736
- atomic: true
- Legal Obligation: unknown
- implement: true
- implementerEnhanced: Default location accuracy of a
  balise group
  [EXTERNAL]
- kind: ordinary

###### A.3.2[2].[t]*.[r][24].Value (Requirement Type)
12 m
- WordTraceId: 296780
- atomic: true
- Legal Obligation: unknown
- implement: true
- kind: ordinary

###### A.3.2[2].[t]*.[r][24].Name (Requirement Type)
Q_NVLOCACC
- WordTraceId: 296785
- atomic: true
- Legal Obligation: unknown
- implement: true
- kind: ordinary

###### A.3.2[2].[t]*.[r][25] (Requirement Type)
- WordTraceId: 296797
- atomic: false
- Legal Obligation: not applicable
- implement: false
- kind: Table

###### A.3.2[2].[t]*.[r][25].Data (Requirement Type)
Weighting factor for available wheel/rail adhesion
- WordTraceId: 296797
- atomic: true
- Legal Obligation: unknown
- implement: true
- kind: ordinary

###### A.3.2[2].[t]*.[r][25].Value (Requirement Type)
0
- WordTraceId: 296848
- atomic: true
- Legal Obligation: unknown
- implement: true
- kind: ordinary

###### A.3.2[2].[t]*.[r][25].Name (Requirement Type)
M_NVAVADH
- WordTraceId: 296850
- atomic: true
- Legal Obligation: unknown
- implement: true
- kind: ordinary

###### A.3.2[2].[t]*.[r][26] (Requirement Type)
- WordTraceId: 296861
- atomic: false
- Legal Obligation: not applicable
- implement: false
- kind: Table

###### A.3.2[2].[t]*.[r][26].Data (Requirement Type)
Confidence level for emergency brake safe deceleration on dry rails
- WordTraceId: 296861
- atomic: true
- Legal Obligation: unknown
- implement: true
- kind: ordinary

###### A.3.2[2].[t]*.[r][26].Value (Requirement Type)
99.9999999 %
- WordTraceId: 296929
- atomic: true
- Legal Obligation: unknown
- implement: true
- kind: ordinary

###### A.3.2[2].[t]*.[r][26].Name (Requirement Type)
M_NVEBCL
- WordTraceId: 296942
- atomic: true
- Legal Obligation: unknown
- implement: true
- kind: ordinary

###### A.3.2[2].[t]*.[r][27] (Requirement Type)
- WordTraceId: 296952
- atomic: false
- Legal Obligation: not applicable
- implement: false
- kind: Table

###### A.3.2[2].[t]*.[r][27].Data (Requirement Type)
Train length step used for the integrated correction factor Kr_int
- WordTraceId: 296952
- atomic: true
- Legal Obligation: unknown
- implement: true
- kind: ordinary

###### A.3.2[2].[t]*.[r][27].Value (Requirement Type)
N/A
- WordTraceId: 297019
- atomic: true
- Legal Obligation: unknown
- implement: true
- kind: ordinary

###### A.3.2[2].[t]*.[r][27].Name (Requirement Type)
L_NVKRINT
- WordTraceId: 297023
- atomic: true
- Legal Obligation: unknown
- implement: true
- kind: ordinary

###### A.3.2[2].[t]*.[r][28] (Requirement Type)
- WordTraceId: 297034
- atomic: false
- Legal Obligation: not applicable
- implement: false
- kind: Table

###### A.3.2[2].[t]*.[r][28].Data (Requirement Type)
Train length dependent integrated correction factor Kr_int
- WordTraceId: 297034
- atomic: true
- Legal Obligation: unknown
- implement: true
- kind: ordinary

###### A.3.2[2].[t]*.[r][28].Value (Requirement Type)
0.9
- WordTraceId: 297093
- atomic: true
- Legal Obligation: unknown
- implement: true
- kind: ordinary

###### A.3.2[2].[t]*.[r][28].Name (Requirement Type)
M_NVKRINT*
- WordTraceId: 297097
- atomic: true
- Legal Obligation: unknown
- implement: true
- kind: ordinary

###### A.3.2[2].[t]*.[r][29] (Requirement Type)
- WordTraceId: 297109
- atomic: false
- Legal Obligation: not applicable
- implement: false
- kind: Table

###### A.3.2[2].[t]*.[r][29].Data (Requirement Type)
Speed step used for the integrated correction factor Kv_int
- WordTraceId: 297109
- atomic: true
- Legal Obligation: unknown
- implement: true
- kind: ordinary

###### A.3.2[2].[t]*.[r][29].Value (Requirement Type)
N/A
- WordTraceId: 297169
- atomic: true
- Legal Obligation: unknown
- implement: true
- kind: ordinary

###### A.3.2[2].[t]*.[r][29].Name (Requirement Type)
V_NVKVINT
- WordTraceId: 297173
- atomic: true
- Legal Obligation: unknown
- implement: true
- kind: ordinary

###### A.3.2[2].[t]*.[r][30] (Requirement Type)
- WordTraceId: 297184
- atomic: false
- Legal Obligation: not applicable
- implement: false
- kind: Table

###### A.3.2[2].[t]*.[r][30].Data (Requirement Type)
Speed dependent integrated correction factor Kv_int
- WordTraceId: 297184
- atomic: true
- Legal Obligation: unknown
- implement: true
- kind: ordinary

###### A.3.2[2].[t]*.[r][30].Value (Requirement Type)
0.7
- WordTraceId: 297236
- atomic: true
- Legal Obligation: unknown
- implement: true
- kind: ordinary

###### A.3.2[2].[t]*.[r][30].Name (Requirement Type)
M_NVKVINT*
- WordTraceId: 297240
- atomic: true
- Legal Obligation: unknown
- implement: true
- kind: ordinary

###### A.3.2[2].[t]*.[r][31] (Requirement Type)
- WordTraceId: 297252
- atomic: false
- Legal Obligation: not applicable
- implement: false
- kind: Table

###### A.3.2[2].[t]*.[r][31].Data (Requirement Type)
Integrated correction factor for brake build up time
- WordTraceId: 297252
- atomic: true
- Legal Obligation: unknown
- implement: true
- implementerEnhanced: Integrated correction factor for brake build up
  time
  [TIME]
- kind: ordinary

###### A.3.2[2].[t]*.[r][31].Value (Requirement Type)
1.1
- WordTraceId: 297305
- atomic: true
- Legal Obligation: unknown
- implement: true
- kind: ordinary
- CrossRefLink -> 1.1

###### A.3.2[2].[t]*.[r][31].Name (Requirement Type)
M_NVKTINT
- WordTraceId: 297309
- atomic: true
- Legal Obligation: unknown
- implement: true
- kind: ordinary

###### A.3.2[2].[t]*.[r][32] (Requirement Type)
- WordTraceId: 297320
- atomic: false
- Legal Obligation: not applicable
- implement: false
- kind: Table

###### A.3.2[2].[t]*.[r][32].Data (Requirement Type)
Maximum deceleration value under reduced adhesion conditions (1)
- WordTraceId: 297320
- atomic: true
- Legal Obligation: unknown
- implement: true
- kind: ordinary

###### A.3.2[2].[t]*.[r][32].Value (Requirement Type)
1.0 m/s 2
- WordTraceId: 297385
- atomic: true
- Legal Obligation: unknown
- PlainText: 1.0 m/s2
- implement: true
- implementerEnhanced: 1.0 m/s2
- kind: ordinary

###### A.3.2[2].[t]*.[r][32].Name (Requirement Type)
A_NVMAXREDADH1
- WordTraceId: 297394
- atomic: true
- Legal Obligation: unknown
- implement: true
- kind: ordinary

###### A.3.2[2].[t]*.[r][33] (Requirement Type)
- WordTraceId: 297410
- atomic: false
- Legal Obligation: not applicable
- implement: false
- kind: Table

###### A.3.2[2].[t]*.[r][33].Data (Requirement Type)
Maximum deceleration value under reduced adhesion conditions (2)
- WordTraceId: 297410
- atomic: true
- Legal Obligation: unknown
- implement: true
- kind: ordinary

###### A.3.2[2].[t]*.[r][33].Value (Requirement Type)
0.7 m/s 2
- WordTraceId: 297475
- atomic: true
- Legal Obligation: unknown
- PlainText: 0.7 m/s2
- implement: true
- implementerEnhanced: 0.7 m/s2
- kind: ordinary

###### A.3.2[2].[t]*.[r][33].Name (Requirement Type)
A_NVMAXREDADH2
- WordTraceId: 297484
- atomic: true
- Legal Obligation: unknown
- implement: true
- kind: ordinary

###### A.3.2[2].[t]*.[r][34] (Requirement Type)
- WordTraceId: 297500
- atomic: false
- Legal Obligation: not applicable
- implement: false
- kind: Table

###### A.3.2[2].[t]*.[r][34].Data (Requirement Type)
Maximum deceleration value under reduced adhesion conditions (3)
- WordTraceId: 297500
- atomic: true
- Legal Obligation: unknown
- implement: true
- kind: ordinary

###### A.3.2[2].[t]*.[r][34].Value (Requirement Type)
0.7 m/s 2
- WordTraceId: 297565
- atomic: true
- Legal Obligation: unknown
- PlainText: 0.7 m/s2
- implement: true
- implementerEnhanced: 0.7 m/s2
- kind: ordinary

###### A.3.2[2].[t]*.[r][34].Name (Requirement Type)
A_NVMAXREDADH3
- WordTraceId: 297574
- atomic: true
- Legal Obligation: unknown
- implement: true
- kind: ordinary

###### A.3.2[2].[t]*.[r][35] (Requirement Type)
- WordTraceId: 297590
- atomic: false
- Legal Obligation: not applicable
- implement: false
- kind: Table

###### A.3.2[2].[t]*.[r][35].Data (Requirement Type)
Lower deceleration limit to determine the set of Kv_int to be used
- WordTraceId: 297590
- atomic: true
- Legal Obligation: unknown
- implement: true
- kind: ordinary

###### A.3.2[2].[t]*.[r][35].Value (Requirement Type)
N/A
- WordTraceId: 297657
- atomic: true
- Legal Obligation: unknown
- implement: true
- kind: ordinary

###### A.3.2[2].[t]*.[r][35].Name (Requirement Type)
A_NVP12
- WordTraceId: 297661
- atomic: true
- Legal Obligation: unknown
- implement: true
- kind: ordinary

###### A.3.2[2].[t]*.[r][36] (Requirement Type)
- WordTraceId: 297670
- atomic: false
- Legal Obligation: not applicable
- implement: false
- kind: Table

###### A.3.2[2].[t]*.[r][36].Data (Requirement Type)
Upper deceleration limit to determine the set of Kv_int to be used
- WordTraceId: 297670
- atomic: true
- Legal Obligation: unknown
- implement: true
- kind: ordinary

###### A.3.2[2].[t]*.[r][36].Value (Requirement Type)
N/A
- WordTraceId: 297737
- atomic: true
- Legal Obligation: unknown
- implement: true
- kind: ordinary

###### A.3.2[2].[t]*.[r][36].Name (Requirement Type)
A_NVP23
- WordTraceId: 297741
- atomic: true
- Legal Obligation: unknown
- implement: true
- kind: ordinary

#### A.3.2[3] (Requirement Type)
*The default value of the correction factor Kr_int shall be valid for any train length, and likewise the default value of the correction factor Kv_int shall be valid for any brake position, speed and maximum emergency brake deceleration. This means that the Kr_int model does not contain any train length step, and that the Kv_int model is valid for all train types and does neither contain any speed step nor any pivot deceleration limit.
- WordTraceId: 297750
- atomic: false
- Legal Obligation: mandatory
- implement: true
- implementerEnhanced: *The default value of the correction factor Kr_int shall be valid for any train length, and likewise the default value of the correction factor Kv_int shall be valid for any brake position, speed and maximum emergency brake deceleration. This means that the Kr_int model does not contain any train length step, and that the Kv_int model is valid
  for all
  [LOOP]
  train types and does neither contain any speed step nor any pivot deceleration limit.
- kind: ordinary

#### A.3.3 (Requirement Type)
A.3.3 Intentionally deleted
- WordTraceId: 298190
- atomic: false
- Legal Obligation: not applicable
- PlainText: Intentionally deleted
- implement: false
- implementerEnhanced: Intentionally deleted
- kind: Placeholder

#### A.3.4 (Requirement Type)
A.3.4 Handling of Accepted and Stored Information in specific Situations
- WordTraceId: 298218
- atomic: false
- Legal Obligation: not applicable
- PlainText: Handling of Accepted and Stored Information in specific Situations
- implement: false
- kind: Heading

##### A.3.4.1 (Requirement Type)
A.3.4.1 Introduction
- WordTraceId: 298291
- atomic: false
- Legal Obligation: not applicable
- PlainText: Introduction
- implement: false
- implementerEnhanced: Introduction
- kind: Heading

###### A.3.4.1.1 (Requirement Type)
A.3.4.1.1 All data that can be stored onboard after being accepted may be influenced in special situations.
- WordTraceId: 298312
- atomic: true
- Legal Obligation: optional
- PlainText: All data that can be stored onboard after being accepted may be influenced in special situations.
- implement: true
- implementerEnhanced: All data that can be stored onboard
  after
  [TIME]
  being accepted may be influenced in special situations.
- kind: ordinary

###### A.3.4.1.2 (Requirement Type)
A.3.4.1.2 The situations acting on the “status” of stored information are:
- WordTraceId: 298420
- atomic: true
- Legal Obligation: unknown
- PlainText: The situations acting on the “status” of stored information are:
- implement: false
- kind: Heading

###### A.3.4.1.2.a (Requirement Type)
the execution of a conditional emergency stop (3.10.2.2);
- WordTraceId: 298495
- atomic: true
- Legal Obligation: unknown
- implement: true
- ListNumberText: a)
- kind: ordinary
- CrossRefLink -> 3.10.2.2

###### A.3.4.1.2.b (Requirement Type)
the reception of a shortened MA (3.8.5.1.3, 3.8.5.1.4);
- WordTraceId: 298553
- atomic: true
- Legal Obligation: unknown
- implement: true
- ListNumberText: b)
- kind: ordinary
- CrossRefLink -> 3.8.5.1.3
- CrossRefLink -> 3.8.5.1.4

###### A.3.4.1.2.c (Requirement Type)
the stored MA is shortened due to a section time-out (3.8.4.2.2);
- WordTraceId: 298609
- atomic: true
- Legal Obligation: unknown
- implement: true
- ListNumberText: c)
- kind: ordinary
- CrossRefLink -> 3.8.4.2.2

###### A.3.4.1.2.d (Requirement Type)
the SvL is shifted (to the DP if any or to the EOA) due to an overlap time-out (3.8.4.4.2) ;
- WordTraceId: 298675
- atomic: true
- Legal Obligation: unknown
- implement: true
- implementerEnhanced: the SvL is shifted (to the DP
  if
  [CONDITION]
  any or to the EOA) due to an overlap time-out (3.8.4.4.2) ;
- ListNumberText: d)
- kind: ordinary
- CrossRefLink -> 3.8.4.4.2

###### A.3.4.1.2.e (Requirement Type)
the stored MA is shortened due to an end section time-out (3.8.4.1.2);
- WordTraceId: 298768
- atomic: true
- Legal Obligation: unknown
- implement: true
- ListNumberText: e)
- kind: ordinary
- CrossRefLink -> 3.8.4.1.2

###### A.3.4.1.2.f (Requirement Type)
a cooperative MA revocation is granted by the onboard (3.8.6.2);
- WordTraceId: 298839
- atomic: true
- Legal Obligation: unknown
- implement: true
- ListNumberText: f)
- kind: ordinary
- CrossRefLink -> 3.8.6.2

###### A.3.4.1.2.g (Requirement Type)
inconsistency in a balise group marked as unlinked and the train is at standstill (3.16.2.5.2);
- WordTraceId: 298904
- atomic: true
- Legal Obligation: unknown
- implement: true
- implementerEnhanced: inconsistency in a
  balise group
  [EXTERNAL]
  marked as unlinked and the train is at standstill (3.16.2.5.2);
- ListNumberText: g)
- kind: ordinary
- CrossRefLink -> 3.16.2.5.2

###### A.3.4.1.2.h (Requirement Type)
a linking reaction led to a service brake and the train is at standstill (3.16.2.6.2) ;
- WordTraceId: 299000
- atomic: true
- Legal Obligation: unknown
- implement: true
- ListNumberText: h)
- kind: ordinary
- CrossRefLink -> 3.16.2.6.2

###### A.3.4.1.2.i (Requirement Type)
the reaction due to the supervision of the safe radio connection led to a service brake and the train is at standstill (3.16.3.4.5 b) ;
- WordTraceId: 299088
- atomic: true
- Legal Obligation: unknown
- implement: true
- ListNumberText: i)
- kind: ordinary
- CrossRefLink -> 3.16.3.4.5.b

###### A.3.4.1.2.j (Requirement Type)
the train category, axle load category, loading gauge or traction system is changed and the train is at standstill (3.18.3.7) ;
- WordTraceId: 299224
- atomic: true
- Legal Obligation: unknown
- implement: true
- ListNumberText: j)
- kind: ordinary
- CrossRefLink -> 3.18.3.7

###### A.3.4.1.2.k (Requirement Type)
driver closes the desk during SoM ;
- WordTraceId: 299352
- atomic: true
- Legal Obligation: unknown
- implement: true
- implementerEnhanced: driver
  [EXTERNAL]
  closes the desk
  during
  [TIME]
  SoM ;
- ListNumberText: k)
- kind: ordinary

###### A.3.4.1.2.l (Requirement Type)
RAMS related supervision functions led to a service brake and the train is at standstill (3.16.2.7)
- WordTraceId: 299388
- atomic: true
- Legal Obligation: unknown
- implement: true
- ListNumberText: l)
- kind: ordinary
- CrossRefLink -> 3.16.2.7

###### A.3.4.1.2.m (Requirement Type)
inconsistency in a balise group marked as linked and no linking is used onboard and the train is at standstill (3.16.2.4.4.2)
- WordTraceId: 299488
- atomic: true
- Legal Obligation: unknown
- implement: true
- implementerEnhanced: inconsistency in a
  balise group
  [EXTERNAL]
  marked as linked and no linking is used onboard and the train is at standstill (3.16.2.4.4.2)
- ListNumberText: m)
- kind: ordinary
- CrossRefLink -> 3.16.2.4.4.2

###### A.3.4.1.2.n (Requirement Type)
the Limit of Authority becomes an End of Authority and the on-board considers an SvL (3.8.4.3.2)
- WordTraceId: 299614
- atomic: true
- Legal Obligation: unknown
- implement: true
- ListNumberText: n)
- kind: ordinary
- CrossRefLink -> 3.8.4.3.2

###### A.3.4.1.3 (Requirement Type)
A.3.4.1.3 Depending on the situation, the action can be:
- WordTraceId: 299711
- atomic: true
- Legal Obligation: unknown
- PlainText: Depending on the situation, the action can be:
- implement: false
- kind: Heading

###### A.3.4.1.3.a (Requirement Type)
data is deleted,
- WordTraceId: 299768
- atomic: true
- Legal Obligation: unknown
- implement: true
- ListNumberText: a)
- kind: ordinary

###### A.3.4.1.3.b (Requirement Type)
data is reset (set to initial states)
- WordTraceId: 299785
- atomic: true
- Legal Obligation: unknown
- implement: true
- ListNumberText: b)
- kind: ordinary

###### A.3.4.1.3.c (Requirement Type)
data status is unchanged,
- WordTraceId: 299823
- atomic: true
- Legal Obligation: unknown
- implement: true
- ListNumberText: c)
- kind: ordinary

###### A.3.4.1.3.d (Requirement Type)
data is to be revalidated
- WordTraceId: 299849
- atomic: true
- Legal Obligation: unknown
- implement: true
- implementerEnhanced: data is to be
  revalidated
  [AGAIN]
- ListNumberText: d)
- kind: ordinary

###### A.3.4.1.3.d[2] (Requirement Type)
- WordTraceId: 299877
- atomic: false
- Legal Obligation: not applicable
- implement: false
- kind: Placeholder

###### A.3.4.1.3.d[2].[t]* (Requirement Type)
| [r][1].D D = Deleted | [r][1].U U = Unchanged | [r][1].R R = Reset | [r][1].TBR TBR = To Be Revalidated |
| --- | --- | --- | --- |
- WordTraceId: 299939
- atomic: false
- Legal Obligation: not applicable
- implement: false
- kind: Table

###### A.3.4.1.3.d[2].[t]*.[r][1] (Requirement Type)
- WordTraceId: 299877
- atomic: false
- Legal Obligation: not applicable
- implement: false
- kind: Table

###### A.3.4.1.3.d[2].[t]*.[r][1].D (Requirement Type)
D = Deleted
- WordTraceId: 299877
- atomic: true
- Legal Obligation: unknown
- implement: true
- kind: ordinary

###### A.3.4.1.3.d[2].[t]*.[r][1].U (Requirement Type)
U = Unchanged
- WordTraceId: 299889
- atomic: true
- Legal Obligation: unknown
- implement: true
- kind: ordinary

###### A.3.4.1.3.d[2].[t]*.[r][1].R (Requirement Type)
R = Reset
- WordTraceId: 299903
- atomic: true
- Legal Obligation: unknown
- implement: true
- kind: ordinary

###### A.3.4.1.3.d[2].[t]*.[r][1].TBR (Requirement Type)
TBR = To Be Revalidated
- WordTraceId: 299913
- atomic: true
- Legal Obligation: unknown
- implement: true
- implementerEnhanced: TBR = To Be
  Revalidated
  [AGAIN]
- kind: ordinary

###### A.3.4.1.3.d[3] (Requirement Type)
- WordTraceId: 299939
- atomic: false
- Legal Obligation: not applicable
- implement: false
- kind: Placeholder

###### A.3.4.1.3.d[3].[t]* (Requirement Type)
| Data Stored on-board | Situations listed above |  |  |
| --- | --- | --- | --- |
| Data Stored on-board | a – d, f, n | e, g – j, l, m | k |
| [r][4].[c][1] National Values | [r][4].[c][2] U | [r][4].[c][3] U | [r][4].[c][4] U |
| [r][5].[c][1] Not yet applicable National Values | [r][5].[c][2] D[1] | [r][5].[c][3] D[10] | [r][5].[c][4] D |
| [r][6].[c][1] Linking | [r][6].[c][2] D[1] | [r][6].[c][3] D[10] | [r][6].[c][4] D |
| [r][7].[c][1] Movement Authority | [r][7].[c][2] D[1] [3] | [r][7].[c][3] D[10] [11] | [r][7].[c][4] D[5] |
| [r][8].[c][1] Gradient Profile | [r][8].[c][2] D[1] | [r][8].[c][3] D[10] | [r][8].[c][4] D |
| [r][9].[c][1] International SSP | [r][9].[c][2] D[1] | [r][9].[c][3] D[10] | [r][9].[c][4] D |
| [r][10].[c][1] Axle load speed profile | [r][10].[c][2] D[1] | [r][10].[c][3] D[10] | [r][10].[c][4] D |
| [r][11].[c][1] STM max speed | [r][11].[c][2] U | [r][11].[c][3] U | [r][11].[c][4] D |
| [r][12].[c][1] STM system speed/distance | [r][12].[c][2] U | [r][12].[c][3] U | [r][12].[c][4] D |
| [r][13].[c][1] Level Transition Order | [r][13].[c][2] U | [r][13].[c][3] U | [r][13].[c][4] D |
| [r][14].[c][1] Stop Shunting on desk opening | [r][14].[c][2] U | [r][14].[c][3] U | [r][14].[c][4] U |
| [r][15].[c][1] List of balises for SH area | [r][15].[c][2] D | [r][15].[c][3] D[9] | [r][15].[c][4] D[5] |
| [r][16].[c][1] MA Request Parameters | [r][16].[c][2] U | [r][16].[c][3] U | [r][16].[c][4] U |
| [r][17].[c][1] Position Report parameters | [r][17].[c][2] U | [r][17].[c][3] U | [r][17].[c][4] U |
| [r][18].[c][1] List of Balises in SR Authority + SR mode speed limit and distance | [r][18].[c][2] U[2] | [r][18].[c][3] U | [r][18].[c][4] D[5] |
| [r][19].[c][1] Temporary Speed Restrictions | [r][19].[c][2] U | [r][19].[c][3] U | [r][19].[c][4] D |
| [r][20].[c][1] Inhibition of revocable TSRs from balises in L2/3 | [r][20].[c][2] U | [r][20].[c][3] U | [r][20].[c][4] D |
| [r][21].[c][1] Default Gradient for TSR | [r][21].[c][2] U[4] | [r][21].[c][3] U[4] | [r][21].[c][4] D |
| [r][22].[c][1] Signalling related Speed Restriction | [r][22].[c][2] D[1] | [r][22].[c][3] D[10] | [r][22].[c][4] D[5] |
| [r][23].[c][1] Route Suitability Data | [r][23].[c][2] D[1] | [r][23].[c][3] D[10] | [r][23].[c][4] D |
| [r][24].[c][1] Plain Text Information (location based) | [r][24].[c][2] D[8] | [r][24].[c][3] D[13] | [r][24].[c][4] D |
| [r][25].[c][1] Plain Text Information (not location based) | [r][25].[c][2] U | [r][25].[c][3] U | [r][25].[c][4] D |
| [r][26].[c][1] Fixed Text Information (location based) | [r][26].[c][2] D[8] | [r][26].[c][3] D[13] | [r][26].[c][4] D |
| [r][27].[c][1] Fixed Text Information (not location based) | [r][27].[c][2] U | [r][27].[c][3] U | [r][27].[c][4] D |
| [r][28].[c][1] Geographical Position | [r][28].[c][2] U | [r][28].[c][3] U | [r][28].[c][4] U |
| [r][29].[c][1] Mode Profile | [r][29].[c][2] D[1] [7] [14] | [r][29].[c][3] D[10] [12] | [r][29].[c][4] D[5] |
| [r][30].[c][1] RBC Transition Order | [r][30].[c][2] D[1] | [r][30].[c][3] D[10] | [r][30].[c][4] D |
| [r][31].[c][1] Radio Infill Area information | [r][31].[c][2] D[1] | [r][31].[c][3] D[10] | [r][31].[c][4] D |
| [r][32].[c][1] EOLM information | [r][32].[c][2] U | [r][32].[c][3] U | [r][32].[c][4] U |
| [r][33].[c][1] Track Conditions excluding big metal masses | [r][33].[c][2] R[1] | [r][33].[c][3] R[10] | [r][33].[c][4] R |
| [r][34].[c][1] Track condition big metal masses | [r][34].[c][2] R[1] | [r][34].[c][3] R[10] | [r][34].[c][4] R |
| [r][35].[c][1] Unconditional Emergency Stop | [r][35].[c][2] U | [r][35].[c][3] U | [r][35].[c][4] D |
| [r][36].[c][1] Conditional Emergency Stop | [r][36].[c][2] U | [r][36].[c][3] U | [r][36].[c][4] D |
| [r][37].[c][1] Train Position | [r][37].[c][2] U | [r][37].[c][3] U | [r][37].[c][4] U |
| [r][38].[c][1] Train Data | [r][38].[c][2] U | [r][38].[c][3] U | [r][38].[c][4] TBR |
| [r][39].[c][1] Adhesion factor | [r][39].[c][2] U | [r][39].[c][3] U | [r][39].[c][4] D |
| [r][40].[c][1] ERTMS/ETCS level | [r][40].[c][2] U | [r][40].[c][3] U | [r][40].[c][4] U |
| [r][41].[c][1] Table of priority of trackside supported levels | [r][41].[c][2] U | [r][41].[c][3] U | [r][41].[c][4] U |
| [r][42].[c][1] Driver ID | [r][42].[c][2] U | [r][42].[c][3] U | [r][42].[c][4] TBR |
| [r][43].[c][1] Radio Network ID | [r][43].[c][2] U | [r][43].[c][3] U | [r][43].[c][4] U |
| [r][44].[c][1] RBC ID/Phone Number | [r][44].[c][2] U | [r][44].[c][3] U | [r][44].[c][4] U |
| [r][45].[c][1] Train Running Number | [r][45].[c][2] U | [r][45].[c][3] U | [r][45].[c][4] TBR |
| [r][46].[c][1] Reversing Area Information | [r][46].[c][2] D[1] | [r][46].[c][3] D[10] | [r][46].[c][4] D |
| [r][47].[c][1] Reversing Supervision Information | [r][47].[c][2] U | [r][47].[c][3] U | [r][47].[c][4] D |
| [r][48].[c][1] Track Ahead Free Request | [r][48].[c][2] U[6] | [r][48].[c][3] U | [r][48].[c][4] D |
| [r][49].[c][1] Level Crossing information | [r][49].[c][2] U | [r][49].[c][3] U | [r][49].[c][4] D |
| [r][50].[c][1] Permitted Braking Distance Information | [r][50].[c][2] D[1] | [r][50].[c][3] D[10] | [r][50].[c][4] D |
| [r][51].[c][1] RBC/RIU System Version | [r][51].[c][2] U | [r][51].[c][3] U | [r][51].[c][4] U |
| [r][52].[c][1] Operated System Version | [r][52].[c][2] U | [r][52].[c][3] U | [r][52].[c][4] U |
| [r][53].[c][1] Language used to display information to the driver | [r][53].[c][2] U | [r][53].[c][3] U | [r][53].[c][4] U |
| [r][54].[c][1] Virtual Balise Covers | [r][54].[c][2] U | [r][54].[c][3] U | [r][54].[c][4] U |
- WordTraceId: 301946
- atomic: false
- Legal Obligation: not applicable
- implement: false
- kind: Table

###### A.3.4.1.3.d[3].[t]*.[r][4] (Requirement Type)
- WordTraceId: 300022
- atomic: false
- Legal Obligation: not applicable
- implement: false
- kind: Table

###### A.3.4.1.3.d[3].[t]*.[r][4].[c][1] (Requirement Type)
National Values
- WordTraceId: 300022
- atomic: true
- Legal Obligation: unknown
- implement: true
- kind: ordinary

###### A.3.4.1.3.d[3].[t]*.[r][4].[c][2] (Requirement Type)
U
- WordTraceId: 300038
- atomic: true
- Legal Obligation: unknown
- implement: true
- kind: ordinary

###### A.3.4.1.3.d[3].[t]*.[r][4].[c][3] (Requirement Type)
U
- WordTraceId: 300040
- atomic: true
- Legal Obligation: unknown
- implement: true
- kind: ordinary

###### A.3.4.1.3.d[3].[t]*.[r][4].[c][4] (Requirement Type)
U
- WordTraceId: 300042
- atomic: true
- Legal Obligation: unknown
- implement: true
- kind: ordinary

###### A.3.4.1.3.d[3].[t]*.[r][5] (Requirement Type)
- WordTraceId: 300045
- atomic: false
- Legal Obligation: not applicable
- implement: false
- kind: Table

###### A.3.4.1.3.d[3].[t]*.[r][5].[c][1] (Requirement Type)
Not yet applicable National Values
- WordTraceId: 300045
- atomic: true
- Legal Obligation: unknown
- implement: true
- implementerEnhanced: Not yet
  [TIME]
  applicable National Values
- kind: ordinary

###### A.3.4.1.3.d[3].[t]*.[r][5].[c][2] (Requirement Type)
D[1]
- WordTraceId: 300080
- atomic: true
- Legal Obligation: unknown
- implement: true
- kind: ordinary

###### A.3.4.1.3.d[3].[t]*.[r][5].[c][3] (Requirement Type)
D[10]
- WordTraceId: 300085
- atomic: true
- Legal Obligation: unknown
- implement: true
- kind: ordinary

###### A.3.4.1.3.d[3].[t]*.[r][5].[c][4] (Requirement Type)
D
- WordTraceId: 300091
- atomic: true
- Legal Obligation: unknown
- implement: true
- kind: ordinary

###### A.3.4.1.3.d[3].[t]*.[r][6] (Requirement Type)
- WordTraceId: 300094
- atomic: false
- Legal Obligation: not applicable
- implement: false
- kind: Table

###### A.3.4.1.3.d[3].[t]*.[r][6].[c][1] (Requirement Type)
Linking
- WordTraceId: 300094
- atomic: true
- Legal Obligation: unknown
- implement: true
- kind: ordinary

###### A.3.4.1.3.d[3].[t]*.[r][6].[c][2] (Requirement Type)
D[1]
- WordTraceId: 300102
- atomic: true
- Legal Obligation: unknown
- implement: true
- kind: ordinary

###### A.3.4.1.3.d[3].[t]*.[r][6].[c][3] (Requirement Type)
D[10]
- WordTraceId: 300107
- atomic: true
- Legal Obligation: unknown
- implement: true
- kind: ordinary

###### A.3.4.1.3.d[3].[t]*.[r][6].[c][4] (Requirement Type)
D
- WordTraceId: 300113
- atomic: true
- Legal Obligation: unknown
- implement: true
- kind: ordinary

###### A.3.4.1.3.d[3].[t]*.[r][7] (Requirement Type)
- WordTraceId: 300116
- atomic: false
- Legal Obligation: not applicable
- implement: false
- kind: Table

###### A.3.4.1.3.d[3].[t]*.[r][7].[c][1] (Requirement Type)
Movement Authority
- WordTraceId: 300116
- atomic: true
- Legal Obligation: unknown
- implement: true
- kind: ordinary

###### A.3.4.1.3.d[3].[t]*.[r][7].[c][2] (Requirement Type)
D[1] [3]
- WordTraceId: 300135
- atomic: true
- Legal Obligation: unknown
- implement: true
- kind: ordinary

###### A.3.4.1.3.d[3].[t]*.[r][7].[c][3] (Requirement Type)
D[10] [11]
- WordTraceId: 300144
- atomic: true
- Legal Obligation: unknown
- implement: true
- kind: ordinary

###### A.3.4.1.3.d[3].[t]*.[r][7].[c][4] (Requirement Type)
D[5]
- WordTraceId: 300155
- atomic: true
- Legal Obligation: unknown
- implement: true
- kind: ordinary

###### A.3.4.1.3.d[3].[t]*.[r][8] (Requirement Type)
- WordTraceId: 300161
- atomic: false
- Legal Obligation: not applicable
- implement: false
- kind: Table

###### A.3.4.1.3.d[3].[t]*.[r][8].[c][1] (Requirement Type)
Gradient Profile
- WordTraceId: 300161
- atomic: true
- Legal Obligation: unknown
- implement: true
- kind: ordinary

###### A.3.4.1.3.d[3].[t]*.[r][8].[c][2] (Requirement Type)
D[1]
- WordTraceId: 300178
- atomic: true
- Legal Obligation: unknown
- implement: true
- kind: ordinary

###### A.3.4.1.3.d[3].[t]*.[r][8].[c][3] (Requirement Type)
D[10]
- WordTraceId: 300183
- atomic: true
- Legal Obligation: unknown
- implement: true
- kind: ordinary

###### A.3.4.1.3.d[3].[t]*.[r][8].[c][4] (Requirement Type)
D
- WordTraceId: 300189
- atomic: true
- Legal Obligation: unknown
- implement: true
- kind: ordinary

###### A.3.4.1.3.d[3].[t]*.[r][9] (Requirement Type)
- WordTraceId: 300192
- atomic: false
- Legal Obligation: not applicable
- implement: false
- kind: Table

###### A.3.4.1.3.d[3].[t]*.[r][9].[c][1] (Requirement Type)
International SSP
- WordTraceId: 300192
- atomic: true
- Legal Obligation: unknown
- implement: true
- kind: ordinary

###### A.3.4.1.3.d[3].[t]*.[r][9].[c][2] (Requirement Type)
D[1]
- WordTraceId: 300210
- atomic: true
- Legal Obligation: unknown
- implement: true
- kind: ordinary

###### A.3.4.1.3.d[3].[t]*.[r][9].[c][3] (Requirement Type)
D[10]
- WordTraceId: 300215
- atomic: true
- Legal Obligation: unknown
- implement: true
- kind: ordinary

###### A.3.4.1.3.d[3].[t]*.[r][9].[c][4] (Requirement Type)
D
- WordTraceId: 300221
- atomic: true
- Legal Obligation: unknown
- implement: true
- kind: ordinary

###### A.3.4.1.3.d[3].[t]*.[r][10] (Requirement Type)
- WordTraceId: 300224
- atomic: false
- Legal Obligation: not applicable
- implement: false
- kind: Table

###### A.3.4.1.3.d[3].[t]*.[r][10].[c][1] (Requirement Type)
Axle load speed profile
- WordTraceId: 300224
- atomic: true
- Legal Obligation: unknown
- implement: true
- kind: ordinary

###### A.3.4.1.3.d[3].[t]*.[r][10].[c][2] (Requirement Type)
D[1]
- WordTraceId: 300248
- atomic: true
- Legal Obligation: unknown
- implement: true
- kind: ordinary

###### A.3.4.1.3.d[3].[t]*.[r][10].[c][3] (Requirement Type)
D[10]
- WordTraceId: 300253
- atomic: true
- Legal Obligation: unknown
- implement: true
- kind: ordinary

###### A.3.4.1.3.d[3].[t]*.[r][10].[c][4] (Requirement Type)
D
- WordTraceId: 300259
- atomic: true
- Legal Obligation: unknown
- implement: true
- kind: ordinary

###### A.3.4.1.3.d[3].[t]*.[r][11] (Requirement Type)
- WordTraceId: 300262
- atomic: false
- Legal Obligation: not applicable
- implement: false
- kind: Table

###### A.3.4.1.3.d[3].[t]*.[r][11].[c][1] (Requirement Type)
STM max speed
- WordTraceId: 300262
- atomic: true
- Legal Obligation: unknown
- implement: true
- kind: ordinary

###### A.3.4.1.3.d[3].[t]*.[r][11].[c][2] (Requirement Type)
U
- WordTraceId: 300276
- atomic: true
- Legal Obligation: unknown
- implement: true
- kind: ordinary

###### A.3.4.1.3.d[3].[t]*.[r][11].[c][3] (Requirement Type)
U
- WordTraceId: 300278
- atomic: true
- Legal Obligation: unknown
- implement: true
- kind: ordinary

###### A.3.4.1.3.d[3].[t]*.[r][11].[c][4] (Requirement Type)
D
- WordTraceId: 300280
- atomic: true
- Legal Obligation: unknown
- implement: true
- kind: ordinary

###### A.3.4.1.3.d[3].[t]*.[r][12] (Requirement Type)
- WordTraceId: 300283
- atomic: false
- Legal Obligation: not applicable
- implement: false
- kind: Table

###### A.3.4.1.3.d[3].[t]*.[r][12].[c][1] (Requirement Type)
STM system speed/distance
- WordTraceId: 300283
- atomic: true
- Legal Obligation: unknown
- implement: true
- kind: ordinary

###### A.3.4.1.3.d[3].[t]*.[r][12].[c][2] (Requirement Type)
U
- WordTraceId: 300309
- atomic: true
- Legal Obligation: unknown
- implement: true
- kind: ordinary

###### A.3.4.1.3.d[3].[t]*.[r][12].[c][3] (Requirement Type)
U
- WordTraceId: 300311
- atomic: true
- Legal Obligation: unknown
- implement: true
- kind: ordinary

###### A.3.4.1.3.d[3].[t]*.[r][12].[c][4] (Requirement Type)
D
- WordTraceId: 300313
- atomic: true
- Legal Obligation: unknown
- implement: true
- kind: ordinary

###### A.3.4.1.3.d[3].[t]*.[r][13] (Requirement Type)
- WordTraceId: 300316
- atomic: false
- Legal Obligation: not applicable
- implement: false
- kind: Table

###### A.3.4.1.3.d[3].[t]*.[r][13].[c][1] (Requirement Type)
Level Transition Order
- WordTraceId: 300316
- atomic: true
- Legal Obligation: unknown
- implement: true
- kind: ordinary

###### A.3.4.1.3.d[3].[t]*.[r][13].[c][2] (Requirement Type)
U
- WordTraceId: 300339
- atomic: true
- Legal Obligation: unknown
- implement: true
- kind: ordinary

###### A.3.4.1.3.d[3].[t]*.[r][13].[c][3] (Requirement Type)
U
- WordTraceId: 300341
- atomic: true
- Legal Obligation: unknown
- implement: true
- kind: ordinary

###### A.3.4.1.3.d[3].[t]*.[r][13].[c][4] (Requirement Type)
D
- WordTraceId: 300343
- atomic: true
- Legal Obligation: unknown
- implement: true
- kind: ordinary

###### A.3.4.1.3.d[3].[t]*.[r][14] (Requirement Type)
- WordTraceId: 300346
- atomic: false
- Legal Obligation: not applicable
- implement: false
- kind: Table

###### A.3.4.1.3.d[3].[t]*.[r][14].[c][1] (Requirement Type)
Stop Shunting on desk opening
- WordTraceId: 300346
- atomic: true
- Legal Obligation: unknown
- implement: true
- kind: ordinary

###### A.3.4.1.3.d[3].[t]*.[r][14].[c][2] (Requirement Type)
U
- WordTraceId: 300376
- atomic: true
- Legal Obligation: unknown
- implement: true
- kind: ordinary

###### A.3.4.1.3.d[3].[t]*.[r][14].[c][3] (Requirement Type)
U
- WordTraceId: 300378
- atomic: true
- Legal Obligation: unknown
- implement: true
- kind: ordinary

###### A.3.4.1.3.d[3].[t]*.[r][14].[c][4] (Requirement Type)
U
- WordTraceId: 300380
- atomic: true
- Legal Obligation: unknown
- implement: true
- kind: ordinary

###### A.3.4.1.3.d[3].[t]*.[r][15] (Requirement Type)
- WordTraceId: 300383
- atomic: false
- Legal Obligation: not applicable
- implement: false
- kind: Table

###### A.3.4.1.3.d[3].[t]*.[r][15].[c][1] (Requirement Type)
List of balises for SH area
- WordTraceId: 300383
- atomic: true
- Legal Obligation: unknown
- implement: true
- implementerEnhanced: List of
  balises
  [EXTERNAL]
  for SH area
- kind: ordinary

###### A.3.4.1.3.d[3].[t]*.[r][15].[c][2] (Requirement Type)
D
- WordTraceId: 300411
- atomic: true
- Legal Obligation: unknown
- implement: true
- kind: ordinary

###### A.3.4.1.3.d[3].[t]*.[r][15].[c][3] (Requirement Type)
D[9]
- WordTraceId: 300413
- atomic: true
- Legal Obligation: unknown
- implement: true
- kind: ordinary

###### A.3.4.1.3.d[3].[t]*.[r][15].[c][4] (Requirement Type)
D[5]
- WordTraceId: 300418
- atomic: true
- Legal Obligation: unknown
- implement: true
- kind: ordinary

###### A.3.4.1.3.d[3].[t]*.[r][16] (Requirement Type)
- WordTraceId: 300424
- atomic: false
- Legal Obligation: not applicable
- implement: false
- kind: Table

###### A.3.4.1.3.d[3].[t]*.[r][16].[c][1] (Requirement Type)
MA Request Parameters
- WordTraceId: 300424
- atomic: true
- Legal Obligation: unknown
- implement: true
- kind: ordinary

###### A.3.4.1.3.d[3].[t]*.[r][16].[c][2] (Requirement Type)
U
- WordTraceId: 300446
- atomic: true
- Legal Obligation: unknown
- implement: true
- kind: ordinary

###### A.3.4.1.3.d[3].[t]*.[r][16].[c][3] (Requirement Type)
U
- WordTraceId: 300448
- atomic: true
- Legal Obligation: unknown
- implement: true
- kind: ordinary

###### A.3.4.1.3.d[3].[t]*.[r][16].[c][4] (Requirement Type)
U
- WordTraceId: 300450
- atomic: true
- Legal Obligation: unknown
- implement: true
- kind: ordinary

###### A.3.4.1.3.d[3].[t]*.[r][17] (Requirement Type)
- WordTraceId: 300453
- atomic: false
- Legal Obligation: not applicable
- implement: false
- kind: Table

###### A.3.4.1.3.d[3].[t]*.[r][17].[c][1] (Requirement Type)
Position Report parameters
- WordTraceId: 300453
- atomic: true
- Legal Obligation: unknown
- implement: true
- kind: ordinary

###### A.3.4.1.3.d[3].[t]*.[r][17].[c][2] (Requirement Type)
U
- WordTraceId: 300480
- atomic: true
- Legal Obligation: unknown
- implement: true
- kind: ordinary

###### A.3.4.1.3.d[3].[t]*.[r][17].[c][3] (Requirement Type)
U
- WordTraceId: 300482
- atomic: true
- Legal Obligation: unknown
- implement: true
- kind: ordinary

###### A.3.4.1.3.d[3].[t]*.[r][17].[c][4] (Requirement Type)
U
- WordTraceId: 300484
- atomic: true
- Legal Obligation: unknown
- implement: true
- kind: ordinary

###### A.3.4.1.3.d[3].[t]*.[r][18] (Requirement Type)
- WordTraceId: 300487
- atomic: false
- Legal Obligation: not applicable
- implement: false
- kind: Table

###### A.3.4.1.3.d[3].[t]*.[r][18].[c][1] (Requirement Type)
List of Balises in SR Authority + SR mode speed limit and distance
- WordTraceId: 300487
- atomic: true
- Legal Obligation: unknown
- implement: true
- implementerEnhanced: List of
  Balises
  [EXTERNAL]
  in SR Authority + SR mode speed limit and distance
- kind: ordinary

###### A.3.4.1.3.d[3].[t]*.[r][18].[c][2] (Requirement Type)
U[2]
- WordTraceId: 300554
- atomic: true
- Legal Obligation: unknown
- implement: true
- kind: ordinary

###### A.3.4.1.3.d[3].[t]*.[r][18].[c][3] (Requirement Type)
U
- WordTraceId: 300559
- atomic: true
- Legal Obligation: unknown
- implement: true
- kind: ordinary

###### A.3.4.1.3.d[3].[t]*.[r][18].[c][4] (Requirement Type)
D[5]
- WordTraceId: 300561
- atomic: true
- Legal Obligation: unknown
- implement: true
- kind: ordinary

###### A.3.4.1.3.d[3].[t]*.[r][19] (Requirement Type)
- WordTraceId: 300567
- atomic: false
- Legal Obligation: not applicable
- implement: false
- kind: Table

###### A.3.4.1.3.d[3].[t]*.[r][19].[c][1] (Requirement Type)
Temporary Speed Restrictions
- WordTraceId: 300567
- atomic: true
- Legal Obligation: unknown
- implement: true
- kind: ordinary

###### A.3.4.1.3.d[3].[t]*.[r][19].[c][2] (Requirement Type)
U
- WordTraceId: 300596
- atomic: true
- Legal Obligation: unknown
- implement: true
- kind: ordinary

###### A.3.4.1.3.d[3].[t]*.[r][19].[c][3] (Requirement Type)
U
- WordTraceId: 300598
- atomic: true
- Legal Obligation: unknown
- implement: true
- kind: ordinary

###### A.3.4.1.3.d[3].[t]*.[r][19].[c][4] (Requirement Type)
D
- WordTraceId: 300600
- atomic: true
- Legal Obligation: unknown
- implement: true
- kind: ordinary

###### A.3.4.1.3.d[3].[t]*.[r][20] (Requirement Type)
- WordTraceId: 300603
- atomic: false
- Legal Obligation: not applicable
- implement: false
- kind: Table

###### A.3.4.1.3.d[3].[t]*.[r][20].[c][1] (Requirement Type)
Inhibition of revocable TSRs from balises in L2/3
- WordTraceId: 300603
- atomic: true
- Legal Obligation: unknown
- implement: true
- implementerEnhanced: Inhibition of revocable TSRs from
  balises
  [EXTERNAL]
  in L2/3
- kind: ordinary

###### A.3.4.1.3.d[3].[t]*.[r][20].[c][2] (Requirement Type)
U
- WordTraceId: 300653
- atomic: true
- Legal Obligation: unknown
- implement: true
- kind: ordinary

###### A.3.4.1.3.d[3].[t]*.[r][20].[c][3] (Requirement Type)
U
- WordTraceId: 300655
- atomic: true
- Legal Obligation: unknown
- implement: true
- kind: ordinary

###### A.3.4.1.3.d[3].[t]*.[r][20].[c][4] (Requirement Type)
D
- WordTraceId: 300657
- atomic: true
- Legal Obligation: unknown
- implement: true
- kind: ordinary

###### A.3.4.1.3.d[3].[t]*.[r][21] (Requirement Type)
- WordTraceId: 300660
- atomic: false
- Legal Obligation: not applicable
- implement: false
- kind: Table

###### A.3.4.1.3.d[3].[t]*.[r][21].[c][1] (Requirement Type)
Default Gradient for TSR
- WordTraceId: 300660
- atomic: true
- Legal Obligation: unknown
- implement: true
- kind: ordinary

###### A.3.4.1.3.d[3].[t]*.[r][21].[c][2] (Requirement Type)
U[4]
- WordTraceId: 300685
- atomic: true
- Legal Obligation: unknown
- implement: true
- kind: ordinary

###### A.3.4.1.3.d[3].[t]*.[r][21].[c][3] (Requirement Type)
U[4]
- WordTraceId: 300690
- atomic: true
- Legal Obligation: unknown
- implement: true
- kind: ordinary

###### A.3.4.1.3.d[3].[t]*.[r][21].[c][4] (Requirement Type)
D
- WordTraceId: 300695
- atomic: true
- Legal Obligation: unknown
- implement: true
- kind: ordinary

###### A.3.4.1.3.d[3].[t]*.[r][22] (Requirement Type)
- WordTraceId: 300698
- atomic: false
- Legal Obligation: not applicable
- implement: false
- kind: Table

###### A.3.4.1.3.d[3].[t]*.[r][22].[c][1] (Requirement Type)
Signalling related Speed Restriction
- WordTraceId: 300698
- atomic: true
- Legal Obligation: unknown
- implement: true
- kind: ordinary

###### A.3.4.1.3.d[3].[t]*.[r][22].[c][2] (Requirement Type)
D[1]
- WordTraceId: 300735
- atomic: true
- Legal Obligation: unknown
- implement: true
- kind: ordinary

###### A.3.4.1.3.d[3].[t]*.[r][22].[c][3] (Requirement Type)
D[10]
- WordTraceId: 300740
- atomic: true
- Legal Obligation: unknown
- implement: true
- kind: ordinary

###### A.3.4.1.3.d[3].[t]*.[r][22].[c][4] (Requirement Type)
D[5]
- WordTraceId: 300746
- atomic: true
- Legal Obligation: unknown
- implement: true
- kind: ordinary

###### A.3.4.1.3.d[3].[t]*.[r][23] (Requirement Type)
- WordTraceId: 300752
- atomic: false
- Legal Obligation: not applicable
- implement: false
- kind: Table

###### A.3.4.1.3.d[3].[t]*.[r][23].[c][1] (Requirement Type)
Route Suitability Data
- WordTraceId: 300752
- atomic: true
- Legal Obligation: unknown
- implement: true
- kind: ordinary

###### A.3.4.1.3.d[3].[t]*.[r][23].[c][2] (Requirement Type)
D[1]
- WordTraceId: 300775
- atomic: true
- Legal Obligation: unknown
- implement: true
- kind: ordinary

###### A.3.4.1.3.d[3].[t]*.[r][23].[c][3] (Requirement Type)
D[10]
- WordTraceId: 300780
- atomic: true
- Legal Obligation: unknown
- implement: true
- kind: ordinary

###### A.3.4.1.3.d[3].[t]*.[r][23].[c][4] (Requirement Type)
D
- WordTraceId: 300786
- atomic: true
- Legal Obligation: unknown
- implement: true
- kind: ordinary

###### A.3.4.1.3.d[3].[t]*.[r][24] (Requirement Type)
- WordTraceId: 300789
- atomic: false
- Legal Obligation: not applicable
- implement: false
- kind: Table

###### A.3.4.1.3.d[3].[t]*.[r][24].[c][1] (Requirement Type)
Plain Text Information (location based)
- WordTraceId: 300789
- atomic: true
- Legal Obligation: unknown
- implement: true
- kind: ordinary

###### A.3.4.1.3.d[3].[t]*.[r][24].[c][2] (Requirement Type)
D[8]
- WordTraceId: 300829
- atomic: true
- Legal Obligation: unknown
- implement: true
- kind: ordinary

###### A.3.4.1.3.d[3].[t]*.[r][24].[c][3] (Requirement Type)
D[13]
- WordTraceId: 300834
- atomic: true
- Legal Obligation: unknown
- implement: true
- kind: ordinary

###### A.3.4.1.3.d[3].[t]*.[r][24].[c][4] (Requirement Type)
D
- WordTraceId: 300840
- atomic: true
- Legal Obligation: unknown
- implement: true
- kind: ordinary

###### A.3.4.1.3.d[3].[t]*.[r][25] (Requirement Type)
- WordTraceId: 300843
- atomic: false
- Legal Obligation: not applicable
- implement: false
- kind: Table

###### A.3.4.1.3.d[3].[t]*.[r][25].[c][1] (Requirement Type)
Plain Text Information (not location based)
- WordTraceId: 300843
- atomic: true
- Legal Obligation: unknown
- implement: true
- kind: ordinary

###### A.3.4.1.3.d[3].[t]*.[r][25].[c][2] (Requirement Type)
U
- WordTraceId: 300887
- atomic: true
- Legal Obligation: unknown
- implement: true
- kind: ordinary

###### A.3.4.1.3.d[3].[t]*.[r][25].[c][3] (Requirement Type)
U
- WordTraceId: 300889
- atomic: true
- Legal Obligation: unknown
- implement: true
- kind: ordinary

###### A.3.4.1.3.d[3].[t]*.[r][25].[c][4] (Requirement Type)
D
- WordTraceId: 300891
- atomic: true
- Legal Obligation: unknown
- implement: true
- kind: ordinary

###### A.3.4.1.3.d[3].[t]*.[r][26] (Requirement Type)
- WordTraceId: 300894
- atomic: false
- Legal Obligation: not applicable
- implement: false
- kind: Table

###### A.3.4.1.3.d[3].[t]*.[r][26].[c][1] (Requirement Type)
Fixed Text Information (location based)
- WordTraceId: 300894
- atomic: true
- Legal Obligation: unknown
- implement: true
- kind: ordinary

###### A.3.4.1.3.d[3].[t]*.[r][26].[c][2] (Requirement Type)
D[8]
- WordTraceId: 300934
- atomic: true
- Legal Obligation: unknown
- implement: true
- kind: ordinary

###### A.3.4.1.3.d[3].[t]*.[r][26].[c][3] (Requirement Type)
D[13]
- WordTraceId: 300939
- atomic: true
- Legal Obligation: unknown
- implement: true
- kind: ordinary

###### A.3.4.1.3.d[3].[t]*.[r][26].[c][4] (Requirement Type)
D
- WordTraceId: 300945
- atomic: true
- Legal Obligation: unknown
- implement: true
- kind: ordinary

###### A.3.4.1.3.d[3].[t]*.[r][27] (Requirement Type)
- WordTraceId: 300948
- atomic: false
- Legal Obligation: not applicable
- implement: false
- kind: Table

###### A.3.4.1.3.d[3].[t]*.[r][27].[c][1] (Requirement Type)
Fixed Text Information (not location based)
- WordTraceId: 300948
- atomic: true
- Legal Obligation: unknown
- implement: true
- kind: ordinary

###### A.3.4.1.3.d[3].[t]*.[r][27].[c][2] (Requirement Type)
U
- WordTraceId: 300992
- atomic: true
- Legal Obligation: unknown
- implement: true
- kind: ordinary

###### A.3.4.1.3.d[3].[t]*.[r][27].[c][3] (Requirement Type)
U
- WordTraceId: 300994
- atomic: true
- Legal Obligation: unknown
- implement: true
- kind: ordinary

###### A.3.4.1.3.d[3].[t]*.[r][27].[c][4] (Requirement Type)
D
- WordTraceId: 300996
- atomic: true
- Legal Obligation: unknown
- implement: true
- kind: ordinary

###### A.3.4.1.3.d[3].[t]*.[r][28] (Requirement Type)
- WordTraceId: 300999
- atomic: false
- Legal Obligation: not applicable
- implement: false
- kind: Table

###### A.3.4.1.3.d[3].[t]*.[r][28].[c][1] (Requirement Type)
Geographical Position
- WordTraceId: 300999
- atomic: true
- Legal Obligation: unknown
- implement: true
- kind: ordinary

###### A.3.4.1.3.d[3].[t]*.[r][28].[c][2] (Requirement Type)
U
- WordTraceId: 301021
- atomic: true
- Legal Obligation: unknown
- implement: true
- kind: ordinary

###### A.3.4.1.3.d[3].[t]*.[r][28].[c][3] (Requirement Type)
U
- WordTraceId: 301023
- atomic: true
- Legal Obligation: unknown
- implement: true
- kind: ordinary

###### A.3.4.1.3.d[3].[t]*.[r][28].[c][4] (Requirement Type)
U
- WordTraceId: 301025
- atomic: true
- Legal Obligation: unknown
- implement: true
- kind: ordinary

###### A.3.4.1.3.d[3].[t]*.[r][29] (Requirement Type)
- WordTraceId: 301028
- atomic: false
- Legal Obligation: not applicable
- implement: false
- kind: Table

###### A.3.4.1.3.d[3].[t]*.[r][29].[c][1] (Requirement Type)
Mode Profile
- WordTraceId: 301028
- atomic: true
- Legal Obligation: unknown
- implement: true
- kind: ordinary

###### A.3.4.1.3.d[3].[t]*.[r][29].[c][2] (Requirement Type)
D[1] [7] [14]
- WordTraceId: 301041
- atomic: true
- Legal Obligation: unknown
- implement: true
- kind: ordinary

###### A.3.4.1.3.d[3].[t]*.[r][29].[c][3] (Requirement Type)
D[10] [12]
- WordTraceId: 301055
- atomic: true
- Legal Obligation: unknown
- implement: true
- kind: ordinary

###### A.3.4.1.3.d[3].[t]*.[r][29].[c][4] (Requirement Type)
D[5]
- WordTraceId: 301066
- atomic: true
- Legal Obligation: unknown
- implement: true
- kind: ordinary

###### A.3.4.1.3.d[3].[t]*.[r][30] (Requirement Type)
- WordTraceId: 301072
- atomic: false
- Legal Obligation: not applicable
- implement: false
- kind: Table

###### A.3.4.1.3.d[3].[t]*.[r][30].[c][1] (Requirement Type)
RBC Transition Order
- WordTraceId: 301072
- atomic: true
- Legal Obligation: unknown
- implement: true
- implementerEnhanced: RBC
  [EXTERNAL]
  Transition Order
- kind: ordinary

###### A.3.4.1.3.d[3].[t]*.[r][30].[c][2] (Requirement Type)
D[1]
- WordTraceId: 301093
- atomic: true
- Legal Obligation: unknown
- implement: true
- kind: ordinary

###### A.3.4.1.3.d[3].[t]*.[r][30].[c][3] (Requirement Type)
D[10]
- WordTraceId: 301098
- atomic: true
- Legal Obligation: unknown
- implement: true
- kind: ordinary

###### A.3.4.1.3.d[3].[t]*.[r][30].[c][4] (Requirement Type)
D
- WordTraceId: 301104
- atomic: true
- Legal Obligation: unknown
- implement: true
- kind: ordinary

###### A.3.4.1.3.d[3].[t]*.[r][31] (Requirement Type)
- WordTraceId: 301107
- atomic: false
- Legal Obligation: not applicable
- implement: false
- kind: Table

###### A.3.4.1.3.d[3].[t]*.[r][31].[c][1] (Requirement Type)
Radio Infill Area information
- WordTraceId: 301107
- atomic: true
- Legal Obligation: unknown
- implement: true
- kind: ordinary

###### A.3.4.1.3.d[3].[t]*.[r][31].[c][2] (Requirement Type)
D[1]
- WordTraceId: 301137
- atomic: true
- Legal Obligation: unknown
- implement: true
- kind: ordinary

###### A.3.4.1.3.d[3].[t]*.[r][31].[c][3] (Requirement Type)
D[10]
- WordTraceId: 301142
- atomic: true
- Legal Obligation: unknown
- implement: true
- kind: ordinary

###### A.3.4.1.3.d[3].[t]*.[r][31].[c][4] (Requirement Type)
D
- WordTraceId: 301148
- atomic: true
- Legal Obligation: unknown
- implement: true
- kind: ordinary

###### A.3.4.1.3.d[3].[t]*.[r][32] (Requirement Type)
- WordTraceId: 301151
- atomic: false
- Legal Obligation: not applicable
- implement: false
- kind: Table

###### A.3.4.1.3.d[3].[t]*.[r][32].[c][1] (Requirement Type)
EOLM information
- WordTraceId: 301151
- atomic: true
- Legal Obligation: unknown
- implement: true
- kind: ordinary

###### A.3.4.1.3.d[3].[t]*.[r][32].[c][2] (Requirement Type)
U
- WordTraceId: 301168
- atomic: true
- Legal Obligation: unknown
- implement: true
- kind: ordinary

###### A.3.4.1.3.d[3].[t]*.[r][32].[c][3] (Requirement Type)
U
- WordTraceId: 301170
- atomic: true
- Legal Obligation: unknown
- implement: true
- kind: ordinary

###### A.3.4.1.3.d[3].[t]*.[r][32].[c][4] (Requirement Type)
U
- WordTraceId: 301172
- atomic: true
- Legal Obligation: unknown
- implement: true
- kind: ordinary

###### A.3.4.1.3.d[3].[t]*.[r][33] (Requirement Type)
- WordTraceId: 301175
- atomic: false
- Legal Obligation: not applicable
- implement: false
- kind: Table

###### A.3.4.1.3.d[3].[t]*.[r][33].[c][1] (Requirement Type)
Track Conditions excluding big metal masses
- WordTraceId: 301175
- atomic: true
- Legal Obligation: unknown
- implement: true
- implementerEnhanced: Track Conditions excluding
  big metal masses
  [LINKED_PHRASE]
- kind: ordinary
- KnownTermLink -> 3.12.1.5.a

###### A.3.4.1.3.d[3].[t]*.[r][33].[c][2] (Requirement Type)
R[1]
- WordTraceId: 301219
- atomic: true
- Legal Obligation: unknown
- implement: true
- kind: ordinary

###### A.3.4.1.3.d[3].[t]*.[r][33].[c][3] (Requirement Type)
R[10]
- WordTraceId: 301224
- atomic: true
- Legal Obligation: unknown
- implement: true
- kind: ordinary

###### A.3.4.1.3.d[3].[t]*.[r][33].[c][4] (Requirement Type)
R
- WordTraceId: 301230
- atomic: true
- Legal Obligation: unknown
- implement: true
- kind: ordinary

###### A.3.4.1.3.d[3].[t]*.[r][34] (Requirement Type)
- WordTraceId: 301233
- atomic: false
- Legal Obligation: not applicable
- implement: false
- kind: Table

###### A.3.4.1.3.d[3].[t]*.[r][34].[c][1] (Requirement Type)
Track condition big metal masses
- WordTraceId: 301233
- atomic: true
- Legal Obligation: unknown
- implement: true
- implementerEnhanced: Track condition
  big metal masses
  [LINKED_PHRASE]
- kind: ordinary
- KnownTermLink -> 3.12.1.5.a

###### A.3.4.1.3.d[3].[t]*.[r][34].[c][2] (Requirement Type)
R[1]
- WordTraceId: 301266
- atomic: true
- Legal Obligation: unknown
- implement: true
- kind: ordinary

###### A.3.4.1.3.d[3].[t]*.[r][34].[c][3] (Requirement Type)
R[10]
- WordTraceId: 301271
- atomic: true
- Legal Obligation: unknown
- implement: true
- kind: ordinary

###### A.3.4.1.3.d[3].[t]*.[r][34].[c][4] (Requirement Type)
R
- WordTraceId: 301277
- atomic: true
- Legal Obligation: unknown
- implement: true
- kind: ordinary

###### A.3.4.1.3.d[3].[t]*.[r][35] (Requirement Type)
- WordTraceId: 301280
- atomic: false
- Legal Obligation: not applicable
- implement: false
- kind: Table

###### A.3.4.1.3.d[3].[t]*.[r][35].[c][1] (Requirement Type)
Unconditional Emergency Stop
- WordTraceId: 301280
- atomic: true
- Legal Obligation: unknown
- implement: true
- kind: ordinary

###### A.3.4.1.3.d[3].[t]*.[r][35].[c][2] (Requirement Type)
U
- WordTraceId: 301309
- atomic: true
- Legal Obligation: unknown
- implement: true
- kind: ordinary

###### A.3.4.1.3.d[3].[t]*.[r][35].[c][3] (Requirement Type)
U
- WordTraceId: 301311
- atomic: true
- Legal Obligation: unknown
- implement: true
- kind: ordinary

###### A.3.4.1.3.d[3].[t]*.[r][35].[c][4] (Requirement Type)
D
- WordTraceId: 301313
- atomic: true
- Legal Obligation: unknown
- implement: true
- kind: ordinary

###### A.3.4.1.3.d[3].[t]*.[r][36] (Requirement Type)
- WordTraceId: 301316
- atomic: false
- Legal Obligation: not applicable
- implement: false
- kind: Table

###### A.3.4.1.3.d[3].[t]*.[r][36].[c][1] (Requirement Type)
Conditional Emergency Stop
- WordTraceId: 301316
- atomic: true
- Legal Obligation: unknown
- implement: true
- kind: ordinary

###### A.3.4.1.3.d[3].[t]*.[r][36].[c][2] (Requirement Type)
U
- WordTraceId: 301343
- atomic: true
- Legal Obligation: unknown
- implement: true
- kind: ordinary

###### A.3.4.1.3.d[3].[t]*.[r][36].[c][3] (Requirement Type)
U
- WordTraceId: 301345
- atomic: true
- Legal Obligation: unknown
- implement: true
- kind: ordinary

###### A.3.4.1.3.d[3].[t]*.[r][36].[c][4] (Requirement Type)
D
- WordTraceId: 301347
- atomic: true
- Legal Obligation: unknown
- implement: true
- kind: ordinary

###### A.3.4.1.3.d[3].[t]*.[r][37] (Requirement Type)
- WordTraceId: 301350
- atomic: false
- Legal Obligation: not applicable
- implement: false
- kind: Table

###### A.3.4.1.3.d[3].[t]*.[r][37].[c][1] (Requirement Type)
Train Position
- WordTraceId: 301350
- atomic: true
- Legal Obligation: unknown
- implement: true
- kind: ordinary

###### A.3.4.1.3.d[3].[t]*.[r][37].[c][2] (Requirement Type)
U
- WordTraceId: 301365
- atomic: true
- Legal Obligation: unknown
- implement: true
- kind: ordinary

###### A.3.4.1.3.d[3].[t]*.[r][37].[c][3] (Requirement Type)
U
- WordTraceId: 301367
- atomic: true
- Legal Obligation: unknown
- implement: true
- kind: ordinary

###### A.3.4.1.3.d[3].[t]*.[r][37].[c][4] (Requirement Type)
U
- WordTraceId: 301369
- atomic: true
- Legal Obligation: unknown
- implement: true
- kind: ordinary

###### A.3.4.1.3.d[3].[t]*.[r][38] (Requirement Type)
- WordTraceId: 301372
- atomic: false
- Legal Obligation: not applicable
- implement: false
- kind: Table

###### A.3.4.1.3.d[3].[t]*.[r][38].[c][1] (Requirement Type)
Train Data
- WordTraceId: 301372
- atomic: true
- Legal Obligation: unknown
- implement: true
- kind: ordinary

###### A.3.4.1.3.d[3].[t]*.[r][38].[c][2] (Requirement Type)
U
- WordTraceId: 301383
- atomic: true
- Legal Obligation: unknown
- implement: true
- kind: ordinary

###### A.3.4.1.3.d[3].[t]*.[r][38].[c][3] (Requirement Type)
U
- WordTraceId: 301385
- atomic: true
- Legal Obligation: unknown
- implement: true
- kind: ordinary

###### A.3.4.1.3.d[3].[t]*.[r][38].[c][4] (Requirement Type)
TBR
- WordTraceId: 301387
- atomic: true
- Legal Obligation: unknown
- implement: true
- kind: ordinary

###### A.3.4.1.3.d[3].[t]*.[r][39] (Requirement Type)
- WordTraceId: 301392
- atomic: false
- Legal Obligation: not applicable
- implement: false
- kind: Table

###### A.3.4.1.3.d[3].[t]*.[r][39].[c][1] (Requirement Type)
Adhesion factor
- WordTraceId: 301392
- atomic: true
- Legal Obligation: unknown
- implement: true
- kind: ordinary

###### A.3.4.1.3.d[3].[t]*.[r][39].[c][2] (Requirement Type)
U
- WordTraceId: 301408
- atomic: true
- Legal Obligation: unknown
- implement: true
- kind: ordinary

###### A.3.4.1.3.d[3].[t]*.[r][39].[c][3] (Requirement Type)
U
- WordTraceId: 301410
- atomic: true
- Legal Obligation: unknown
- implement: true
- kind: ordinary

###### A.3.4.1.3.d[3].[t]*.[r][39].[c][4] (Requirement Type)
D
- WordTraceId: 301412
- atomic: true
- Legal Obligation: unknown
- implement: true
- kind: ordinary

###### A.3.4.1.3.d[3].[t]*.[r][40] (Requirement Type)
- WordTraceId: 301415
- atomic: false
- Legal Obligation: not applicable
- implement: false
- kind: Table

###### A.3.4.1.3.d[3].[t]*.[r][40].[c][1] (Requirement Type)
ERTMS/ETCS level
- WordTraceId: 301415
- atomic: true
- Legal Obligation: unknown
- implement: true
- kind: ordinary

###### A.3.4.1.3.d[3].[t]*.[r][40].[c][2] (Requirement Type)
U
- WordTraceId: 301432
- atomic: true
- Legal Obligation: unknown
- implement: true
- kind: ordinary

###### A.3.4.1.3.d[3].[t]*.[r][40].[c][3] (Requirement Type)
U
- WordTraceId: 301434
- atomic: true
- Legal Obligation: unknown
- implement: true
- kind: ordinary

###### A.3.4.1.3.d[3].[t]*.[r][40].[c][4] (Requirement Type)
U
- WordTraceId: 301436
- atomic: true
- Legal Obligation: unknown
- implement: true
- kind: ordinary

###### A.3.4.1.3.d[3].[t]*.[r][41] (Requirement Type)
- WordTraceId: 301439
- atomic: false
- Legal Obligation: not applicable
- implement: false
- kind: Table

###### A.3.4.1.3.d[3].[t]*.[r][41].[c][1] (Requirement Type)
Table of priority of trackside supported levels
- WordTraceId: 301439
- atomic: true
- Legal Obligation: unknown
- implement: true
- implementerEnhanced: Table of priority of
  trackside
  [EXTERNAL]
  supported levels
- kind: ordinary

###### A.3.4.1.3.d[3].[t]*.[r][41].[c][2] (Requirement Type)
U
- WordTraceId: 301487
- atomic: true
- Legal Obligation: unknown
- implement: true
- kind: ordinary

###### A.3.4.1.3.d[3].[t]*.[r][41].[c][3] (Requirement Type)
U
- WordTraceId: 301489
- atomic: true
- Legal Obligation: unknown
- implement: true
- kind: ordinary

###### A.3.4.1.3.d[3].[t]*.[r][41].[c][4] (Requirement Type)
U
- WordTraceId: 301491
- atomic: true
- Legal Obligation: unknown
- implement: true
- kind: ordinary

###### A.3.4.1.3.d[3].[t]*.[r][42] (Requirement Type)
- WordTraceId: 301494
- atomic: false
- Legal Obligation: not applicable
- implement: false
- kind: Table

###### A.3.4.1.3.d[3].[t]*.[r][42].[c][1] (Requirement Type)
Driver ID
- WordTraceId: 301494
- atomic: true
- Legal Obligation: unknown
- implement: true
- kind: ordinary

###### A.3.4.1.3.d[3].[t]*.[r][42].[c][2] (Requirement Type)
U
- WordTraceId: 301504
- atomic: true
- Legal Obligation: unknown
- implement: true
- kind: ordinary

###### A.3.4.1.3.d[3].[t]*.[r][42].[c][3] (Requirement Type)
U
- WordTraceId: 301506
- atomic: true
- Legal Obligation: unknown
- implement: true
- kind: ordinary

###### A.3.4.1.3.d[3].[t]*.[r][42].[c][4] (Requirement Type)
TBR
- WordTraceId: 301508
- atomic: true
- Legal Obligation: unknown
- implement: true
- kind: ordinary

###### A.3.4.1.3.d[3].[t]*.[r][43] (Requirement Type)
- WordTraceId: 301513
- atomic: false
- Legal Obligation: not applicable
- implement: false
- kind: Table

###### A.3.4.1.3.d[3].[t]*.[r][43].[c][1] (Requirement Type)
Radio Network ID
- WordTraceId: 301513
- atomic: true
- Legal Obligation: unknown
- implement: true
- kind: ordinary

###### A.3.4.1.3.d[3].[t]*.[r][43].[c][2] (Requirement Type)
U
- WordTraceId: 301530
- atomic: true
- Legal Obligation: unknown
- implement: true
- kind: ordinary

###### A.3.4.1.3.d[3].[t]*.[r][43].[c][3] (Requirement Type)
U
- WordTraceId: 301532
- atomic: true
- Legal Obligation: unknown
- implement: true
- kind: ordinary

###### A.3.4.1.3.d[3].[t]*.[r][43].[c][4] (Requirement Type)
U
- WordTraceId: 301534
- atomic: true
- Legal Obligation: unknown
- implement: true
- kind: ordinary

###### A.3.4.1.3.d[3].[t]*.[r][44] (Requirement Type)
- WordTraceId: 301537
- atomic: false
- Legal Obligation: not applicable
- implement: false
- kind: Table

###### A.3.4.1.3.d[3].[t]*.[r][44].[c][1] (Requirement Type)
RBC ID/Phone Number
- WordTraceId: 301537
- atomic: true
- Legal Obligation: unknown
- implement: true
- kind: ordinary

###### A.3.4.1.3.d[3].[t]*.[r][44].[c][2] (Requirement Type)
U
- WordTraceId: 301557
- atomic: true
- Legal Obligation: unknown
- implement: true
- kind: ordinary

###### A.3.4.1.3.d[3].[t]*.[r][44].[c][3] (Requirement Type)
U
- WordTraceId: 301559
- atomic: true
- Legal Obligation: unknown
- implement: true
- kind: ordinary

###### A.3.4.1.3.d[3].[t]*.[r][44].[c][4] (Requirement Type)
U
- WordTraceId: 301561
- atomic: true
- Legal Obligation: unknown
- implement: true
- kind: ordinary

###### A.3.4.1.3.d[3].[t]*.[r][45] (Requirement Type)
- WordTraceId: 301564
- atomic: false
- Legal Obligation: not applicable
- implement: false
- kind: Table

###### A.3.4.1.3.d[3].[t]*.[r][45].[c][1] (Requirement Type)
Train Running Number
- WordTraceId: 301564
- atomic: true
- Legal Obligation: unknown
- implement: true
- kind: ordinary

###### A.3.4.1.3.d[3].[t]*.[r][45].[c][2] (Requirement Type)
U
- WordTraceId: 301585
- atomic: true
- Legal Obligation: unknown
- implement: true
- kind: ordinary

###### A.3.4.1.3.d[3].[t]*.[r][45].[c][3] (Requirement Type)
U
- WordTraceId: 301587
- atomic: true
- Legal Obligation: unknown
- implement: true
- kind: ordinary

###### A.3.4.1.3.d[3].[t]*.[r][45].[c][4] (Requirement Type)
TBR
- WordTraceId: 301589
- atomic: true
- Legal Obligation: unknown
- implement: true
- kind: ordinary

###### A.3.4.1.3.d[3].[t]*.[r][46] (Requirement Type)
- WordTraceId: 301594
- atomic: false
- Legal Obligation: not applicable
- implement: false
- kind: Table

###### A.3.4.1.3.d[3].[t]*.[r][46].[c][1] (Requirement Type)
Reversing Area Information
- WordTraceId: 301594
- atomic: true
- Legal Obligation: unknown
- implement: true
- kind: ordinary

###### A.3.4.1.3.d[3].[t]*.[r][46].[c][2] (Requirement Type)
D[1]
- WordTraceId: 301621
- atomic: true
- Legal Obligation: unknown
- implement: true
- kind: ordinary

###### A.3.4.1.3.d[3].[t]*.[r][46].[c][3] (Requirement Type)
D[10]
- WordTraceId: 301626
- atomic: true
- Legal Obligation: unknown
- implement: true
- kind: ordinary

###### A.3.4.1.3.d[3].[t]*.[r][46].[c][4] (Requirement Type)
D
- WordTraceId: 301632
- atomic: true
- Legal Obligation: unknown
- implement: true
- kind: ordinary

###### A.3.4.1.3.d[3].[t]*.[r][47] (Requirement Type)
- WordTraceId: 301635
- atomic: false
- Legal Obligation: not applicable
- implement: false
- kind: Table

###### A.3.4.1.3.d[3].[t]*.[r][47].[c][1] (Requirement Type)
Reversing Supervision Information
- WordTraceId: 301635
- atomic: true
- Legal Obligation: unknown
- implement: true
- kind: ordinary

###### A.3.4.1.3.d[3].[t]*.[r][47].[c][2] (Requirement Type)
U
- WordTraceId: 301669
- atomic: true
- Legal Obligation: unknown
- implement: true
- kind: ordinary

###### A.3.4.1.3.d[3].[t]*.[r][47].[c][3] (Requirement Type)
U
- WordTraceId: 301671
- atomic: true
- Legal Obligation: unknown
- implement: true
- kind: ordinary

###### A.3.4.1.3.d[3].[t]*.[r][47].[c][4] (Requirement Type)
D
- WordTraceId: 301673
- atomic: true
- Legal Obligation: unknown
- implement: true
- kind: ordinary

###### A.3.4.1.3.d[3].[t]*.[r][48] (Requirement Type)
- WordTraceId: 301676
- atomic: false
- Legal Obligation: not applicable
- implement: false
- kind: Table

###### A.3.4.1.3.d[3].[t]*.[r][48].[c][1] (Requirement Type)
Track Ahead Free Request
- WordTraceId: 301676
- atomic: true
- Legal Obligation: unknown
- implement: true
- kind: ordinary

###### A.3.4.1.3.d[3].[t]*.[r][48].[c][2] (Requirement Type)
U[6]
- WordTraceId: 301701
- atomic: true
- Legal Obligation: unknown
- implement: true
- kind: ordinary

###### A.3.4.1.3.d[3].[t]*.[r][48].[c][3] (Requirement Type)
U
- WordTraceId: 301706
- atomic: true
- Legal Obligation: unknown
- implement: true
- kind: ordinary

###### A.3.4.1.3.d[3].[t]*.[r][48].[c][4] (Requirement Type)
D
- WordTraceId: 301708
- atomic: true
- Legal Obligation: unknown
- implement: true
- kind: ordinary

###### A.3.4.1.3.d[3].[t]*.[r][49] (Requirement Type)
- WordTraceId: 301711
- atomic: false
- Legal Obligation: not applicable
- implement: false
- kind: Table

###### A.3.4.1.3.d[3].[t]*.[r][49].[c][1] (Requirement Type)
Level Crossing information
- WordTraceId: 301711
- atomic: true
- Legal Obligation: unknown
- implement: true
- kind: ordinary

###### A.3.4.1.3.d[3].[t]*.[r][49].[c][2] (Requirement Type)
U
- WordTraceId: 301738
- atomic: true
- Legal Obligation: unknown
- implement: true
- kind: ordinary

###### A.3.4.1.3.d[3].[t]*.[r][49].[c][3] (Requirement Type)
U
- WordTraceId: 301740
- atomic: true
- Legal Obligation: unknown
- implement: true
- kind: ordinary

###### A.3.4.1.3.d[3].[t]*.[r][49].[c][4] (Requirement Type)
D
- WordTraceId: 301742
- atomic: true
- Legal Obligation: unknown
- implement: true
- kind: ordinary

###### A.3.4.1.3.d[3].[t]*.[r][50] (Requirement Type)
- WordTraceId: 301745
- atomic: false
- Legal Obligation: not applicable
- implement: false
- kind: Table

###### A.3.4.1.3.d[3].[t]*.[r][50].[c][1] (Requirement Type)
Permitted Braking Distance Information
- WordTraceId: 301745
- atomic: true
- Legal Obligation: unknown
- implement: true
- kind: ordinary

###### A.3.4.1.3.d[3].[t]*.[r][50].[c][2] (Requirement Type)
D[1]
- WordTraceId: 301784
- atomic: true
- Legal Obligation: unknown
- implement: true
- kind: ordinary

###### A.3.4.1.3.d[3].[t]*.[r][50].[c][3] (Requirement Type)
D[10]
- WordTraceId: 301789
- atomic: true
- Legal Obligation: unknown
- implement: true
- kind: ordinary

###### A.3.4.1.3.d[3].[t]*.[r][50].[c][4] (Requirement Type)
D
- WordTraceId: 301795
- atomic: true
- Legal Obligation: unknown
- implement: true
- kind: ordinary

###### A.3.4.1.3.d[3].[t]*.[r][51] (Requirement Type)
- WordTraceId: 301798
- atomic: false
- Legal Obligation: not applicable
- implement: false
- kind: Table

###### A.3.4.1.3.d[3].[t]*.[r][51].[c][1] (Requirement Type)
RBC/RIU System Version
- WordTraceId: 301798
- atomic: true
- Legal Obligation: unknown
- implement: true
- implementerEnhanced: RBC
  [EXTERNAL]
  /
  RIU
  [EXTERNAL]
  System Version
- kind: ordinary

###### A.3.4.1.3.d[3].[t]*.[r][51].[c][2] (Requirement Type)
U
- WordTraceId: 301821
- atomic: true
- Legal Obligation: unknown
- implement: true
- kind: ordinary

###### A.3.4.1.3.d[3].[t]*.[r][51].[c][3] (Requirement Type)
U
- WordTraceId: 301823
- atomic: true
- Legal Obligation: unknown
- implement: true
- kind: ordinary

###### A.3.4.1.3.d[3].[t]*.[r][51].[c][4] (Requirement Type)
U
- WordTraceId: 301825
- atomic: true
- Legal Obligation: unknown
- implement: true
- kind: ordinary

###### A.3.4.1.3.d[3].[t]*.[r][52] (Requirement Type)
- WordTraceId: 301828
- atomic: false
- Legal Obligation: not applicable
- implement: false
- kind: Table

###### A.3.4.1.3.d[3].[t]*.[r][52].[c][1] (Requirement Type)
Operated System Version
- WordTraceId: 301828
- atomic: true
- Legal Obligation: unknown
- implement: true
- kind: ordinary

###### A.3.4.1.3.d[3].[t]*.[r][52].[c][2] (Requirement Type)
U
- WordTraceId: 301852
- atomic: true
- Legal Obligation: unknown
- implement: true
- kind: ordinary

###### A.3.4.1.3.d[3].[t]*.[r][52].[c][3] (Requirement Type)
U
- WordTraceId: 301854
- atomic: true
- Legal Obligation: unknown
- implement: true
- kind: ordinary

###### A.3.4.1.3.d[3].[t]*.[r][52].[c][4] (Requirement Type)
U
- WordTraceId: 301856
- atomic: true
- Legal Obligation: unknown
- implement: true
- kind: ordinary

###### A.3.4.1.3.d[3].[t]*.[r][53] (Requirement Type)
- WordTraceId: 301859
- atomic: false
- Legal Obligation: not applicable
- implement: false
- kind: Table

###### A.3.4.1.3.d[3].[t]*.[r][53].[c][1] (Requirement Type)
Language used to display information to the driver
- WordTraceId: 301859
- atomic: true
- Legal Obligation: unknown
- implement: true
- implementerEnhanced: Language used to display information to the
  driver
  [EXTERNAL]
- kind: ordinary

###### A.3.4.1.3.d[3].[t]*.[r][53].[c][2] (Requirement Type)
U
- WordTraceId: 301910
- atomic: true
- Legal Obligation: unknown
- implement: true
- kind: ordinary

###### A.3.4.1.3.d[3].[t]*.[r][53].[c][3] (Requirement Type)
U
- WordTraceId: 301912
- atomic: true
- Legal Obligation: unknown
- implement: true
- kind: ordinary

###### A.3.4.1.3.d[3].[t]*.[r][53].[c][4] (Requirement Type)
U
- WordTraceId: 301914
- atomic: true
- Legal Obligation: unknown
- implement: true
- kind: ordinary

###### A.3.4.1.3.d[3].[t]*.[r][54] (Requirement Type)
- WordTraceId: 301917
- atomic: false
- Legal Obligation: not applicable
- implement: false
- kind: Table

###### A.3.4.1.3.d[3].[t]*.[r][54].[c][1] (Requirement Type)
Virtual Balise Covers
- WordTraceId: 301917
- atomic: true
- Legal Obligation: unknown
- implement: true
- implementerEnhanced: Virtual
  Balise
  [EXTERNAL]
  Covers
- kind: ordinary

###### A.3.4.1.3.d[3].[t]*.[r][54].[c][2] (Requirement Type)
U
- WordTraceId: 301939
- atomic: true
- Legal Obligation: unknown
- implement: true
- kind: ordinary

###### A.3.4.1.3.d[3].[t]*.[r][54].[c][3] (Requirement Type)
U
- WordTraceId: 301941
- atomic: true
- Legal Obligation: unknown
- implement: true
- kind: ordinary

###### A.3.4.1.3.d[3].[t]*.[r][54].[c][4] (Requirement Type)
U
- WordTraceId: 301943
- atomic: true
- Legal Obligation: unknown
- implement: true
- kind: ordinary

###### A.3.4.1.3.d[4] (Requirement Type)
[1]: beyond the new SvL
or in case of situation a, beyond the stop location of the accepted CES
- WordTraceId: 301946
- atomic: true
- Legal Obligation: unknown
- implement: true
- implementerEnhanced: [1]: beyond the new SvL or
  in case of
  [CONDITION]
  situation a, beyond the stop location of the accepted CES
- kind: ordinary

###### A.3.4.1.3.d[5] (Requirement Type)
[2]: The considered situations cannot occur when a list of balises to be used in SR is available onboard. Indeed, the onboard is in SR mode and since no MA or track description are stored onboard, no new SvL may be defined.
- WordTraceId: 302042
- atomic: false
- Legal Obligation: optional
- implement: true
- implementerEnhanced: [2]: The considered situations cannot occur
  when
  [CONDITION]
  a list of
  balises
  [EXTERNAL]
  to be used in SR is available onboard. Indeed, the onboard is in SR mode and since no MA or track description are stored onboard, no new SvL may be defined.
- kind: ordinary

###### A.3.4.1.3.d[6] (Requirement Type)
[3]: In case of reception of a new non-infill MA (situation b or f), the stored MA is fully replaced with the new one. In case of reception of a new infill MA (situation b), the stored MA is replaced beyond the infill location reference, i.e. the balise group at the next main signal
- WordTraceId: 302266
- atomic: false
- Legal Obligation: unknown
- implement: true
- implementerEnhanced: [3]:
  In case of
  [CONDITION]
  reception of a new non-infill MA (situation b or f), the stored MA is fully replaced with the new one.
  In case of
  [CONDITION]
  reception of a new infill MA (situation b), the stored MA is replaced beyond the infill location reference, i.e. the
  balise group
  [EXTERNAL]
  at the next main signal
- kind: ordinary

###### A.3.4.1.3.d[7] (Requirement Type)
[4]: The considered situations a-d, f, h, i cannot occur when the default gradient for a TSR is used on-board.
- WordTraceId: 302550
- atomic: true
- Legal Obligation: unknown
- implement: true
- implementerEnhanced: [4]: The considered situations a-d, f, h, i cannot occur
  when
  [CONDITION]
  the default gradient for a TSR is used on-board.
- kind: ordinary

###### A.3.4.1.3.d[8] (Requirement Type)
[5]: The considered situation cannot occur because acceptance of this information has led to exit from SoM procedure.
- WordTraceId: 302661
- atomic: true
- Legal Obligation: unknown
- implement: true
- kind: ordinary

###### A.3.4.1.3.d[9] (Requirement Type)
[6]: The considered situations b-d, f cannot occur when a TAF request is stored on-board
- WordTraceId: 302779
- atomic: true
- Legal Obligation: unknown
- implement: true
- implementerEnhanced: [6]: The considered situations b-d, f cannot occur
  when
  [CONDITION]
  a TAF request is stored on-board
- kind: ordinary

###### A.3.4.1.3.d[10] (Requirement Type)
[7]: If the start location of the Mode Profile is beyond the new SvL, the acknowledgement window of the Mode Profile shall be deleted as well
- WordTraceId: 302868
- atomic: true
- Legal Obligation: mandatory
- implement: true
- implementerEnhanced: [7]:
  If
  [CONDITION]
  the start location of the Mode Profile is beyond the new SvL, the acknowledgement window of the Mode Profile shall be deleted as well
- kind: ordinary

###### A.3.4.1.3.d[11] (Requirement Type)
[8]: only if the location where to start to display the text is beyond the new SvL; otherwise all the text information (i.e. including end location where to stop display, if any) shall remain unchanged
- WordTraceId: 303010
- atomic: false
- Legal Obligation: mandatory
- implement: true
- implementerEnhanced: [8]: only
  if
  [CONDITION]
  the location where to start to display the text is beyond the new SvL; otherwise all the text information (i.e. including end location where to stop display,
  if
  [CONDITION]
  any) shall remain unchanged
- kind: ordinary

###### A.3.4.1.3.d[12] (Requirement Type)
[9]: unchanged if the onboard is in SH mode
- WordTraceId: 303212
- atomic: true
- Legal Obligation: unknown
- implement: true
- implementerEnhanced: [9]: unchanged
  if
  [CONDITION]
  the onboard is in SH mode
- kind: ordinary

###### A.3.4.1.3.d[13] (Requirement Type)
[10]: beyond the current max safe front end position of the train
- WordTraceId: 303256
- atomic: true
- Legal Obligation: unknown
- implement: true
- kind: ordinary

###### A.3.4.1.3.d[14] (Requirement Type)
[11]: the ERTMS/ETCS on-board equipment shall consider the current estimated front end and max safe front end positions of the train, as the EOA and SvL respectively, with no release speed
- WordTraceId: 303322
- atomic: true
- Legal Obligation: mandatory
- implement: true
- implementerEnhanced: [11]: the
  ERTMS/ETCS on-board equipment
  [SELF]
  shall consider the current estimated front end and max safe front end positions of the train, as the EOA and SvL respectively, with no release speed
- kind: ordinary

###### A.3.4.1.3.d[15] (Requirement Type)
[12]: If the start location of the Mode Profile is beyond the current max safe front end, the acknowledgement window of the Mode Profile shall be deleted as well
- WordTraceId: 303511
- atomic: true
- Legal Obligation: mandatory
- implement: true
- implementerEnhanced: [12]:
  If
  [CONDITION]
  the start location of the Mode Profile is beyond the current max safe front end, the acknowledgement window of the Mode Profile shall be deleted as well
- kind: ordinary

###### A.3.4.1.3.d[16] (Requirement Type)
[13]: only if the location where to start to display the text is beyond the current max safe front end; otherwise all the text information (i.e. including end location where to stop display, if any) shall remain unchanged
- WordTraceId: 303673
- atomic: false
- Legal Obligation: mandatory
- implement: true
- implementerEnhanced: [13]: only
  if
  [CONDITION]
  the location where to start to display the text is beyond the current max safe front end; otherwise all the text information (i.e. including end location where to stop display,
  if
  [CONDITION]
  any) shall remain unchanged
- kind: ordinary

###### A.3.4.1.3.d[17] (Requirement Type)
[14]: In case of reception of a new non-infill MA with or without Mode Profile (situation b or f), the stored Mode Profile is deleted. In case of reception of a new infill MA (situation b), the stored Mode Profile is deleted only beyond the infill location reference, i.e. the balise group at the next main signal
- WordTraceId: 303895
- atomic: false
- Legal Obligation: unknown
- implement: true
- implementerEnhanced: [14]:
  In case of
  [CONDITION]
  reception of a new non-infill MA with or without Mode Profile (situation b or f), the stored Mode Profile is deleted.
  In case of
  [CONDITION]
  reception of a new infill MA (situation b), the stored Mode Profile is deleted only beyond the infill location reference, i.e. the
  balise group
  [EXTERNAL]
  at the next main signal
- kind: ordinary

###### A.3.4.1.4 (Requirement Type)
A.3.4.1.4 NOTES:
- WordTraceId: 304210
- atomic: true
- Legal Obligation: unknown
- PlainText: NOTES:
- implement: false
- implementerEnhanced: NOTES:
- kind: Heading

###### A.3.4.1.4.1 (Requirement Type)
A.3.4.1.4.1 “Location” contains LRBG, distance travelled from LRBG, position of the front end in relation to the LRBG, the confidence interval and the orientation in relation to the LRBG.
- WordTraceId: 304227
- atomic: true
- Legal Obligation: unknown
- PlainText: “Location” contains LRBG, distance travelled from LRBG, position of the front end in relation to the LRBG, the confidence interval and the orientation in relation to the LRBG.
- implement: true
- implementerEnhanced: “Location” contains
  LRBG
  [EXTERNAL]
  , distance travelled from
  LRBG
  [EXTERNAL]
  , position of the front end in relation to the
  LRBG
  [EXTERNAL]
  , the confidence interval and the orientation in relation to the
  LRBG
  [EXTERNAL]
  .
- kind: ordinary

###### A.3.4.1.4.2 (Requirement Type)
A.3.4.1.4.2 The following information is not considered to be stored information:
- WordTraceId: 304415
- atomic: true
- Legal Obligation: unknown
- PlainText: The following information is not considered to be stored information:
- implement: false
- kind: Heading

###### A.3.4.1.4.2.a (Requirement Type)
Repositioning information
- WordTraceId: 304497
- atomic: true
- Legal Obligation: unknown
- implement: true
- ListNumberText: a)
- kind: ordinary

###### A.3.4.1.4.2.b (Requirement Type)
Session Management (exception: the RBC ID/phone number, which is given with an order to establish a communication session, is stored on-board)
- WordTraceId: 304523
- atomic: true
- Legal Obligation: unknown
- implement: true
- ListNumberText: b)
- kind: ordinary

###### A.3.4.1.4.2.c (Requirement Type)
Danger for SH information
- WordTraceId: 304666
- atomic: true
- Legal Obligation: unknown
- implement: true
- ListNumberText: c)
- kind: ordinary

###### A.3.4.1.4.2.d (Requirement Type)
Assignment of Co-ordinate system
- WordTraceId: 304692
- atomic: true
- Legal Obligation: unknown
- implement: true
- ListNumberText: d)
- kind: ordinary

###### A.3.4.1.4.2.e (Requirement Type)
Infill Location Reference
- WordTraceId: 304725
- atomic: true
- Legal Obligation: unknown
- implement: true
- ListNumberText: e)
- kind: ordinary

###### A.3.4.1.4.2.f (Requirement Type)
Location Identity (NID_C + NID_BG transmitted in the balise telegram)
- WordTraceId: 304751
- atomic: true
- Legal Obligation: unknown
- implement: true
- ListNumberText: f)
- kind: ordinary

###### A.3.4.1.4.2.g (Requirement Type)
Recognition of exit from TRIP mode
- WordTraceId: 304821
- atomic: true
- Legal Obligation: unknown
- implement: true
- ListNumberText: g)
- kind: ordinary

###### A.3.4.1.4.2.h (Requirement Type)
Acknowledgement of Train Data
- WordTraceId: 304856
- atomic: true
- Legal Obligation: unknown
- implement: true
- ListNumberText: h)
- kind: ordinary

###### A.3.4.1.4.2.i (Requirement Type)
SH refused
- WordTraceId: 304887
- atomic: true
- Legal Obligation: unknown
- implement: true
- ListNumberText: i)
- kind: ordinary

###### A.3.4.1.4.2.j (Requirement Type)
SH authorised
- WordTraceId: 304898
- atomic: true
- Legal Obligation: unknown
- implement: true
- ListNumberText: j)
- kind: ordinary

###### A.3.4.1.4.2.k (Requirement Type)
Balise/loop system version
- WordTraceId: 304912
- atomic: true
- Legal Obligation: unknown
- implement: true
- implementerEnhanced: Balise
  [EXTERNAL]
  /
  loop
  [EXTERNAL]
  system version
- ListNumberText: k)
- kind: ordinary

###### A.3.4.1.4.2.l (Requirement Type)
Track Condition Station Platforms
- WordTraceId: 304939
- atomic: true
- Legal Obligation: unknown
- implement: true
- implementerEnhanced: Track Condition
  Station Platforms
  [LINKED_PHRASE]
- ListNumberText: l)
- kind: ordinary
- KnownTermLink -> 3.12.1.5.a

###### A.3.4.1.4.2.m (Requirement Type)
Track Condition Change of Allowed Current Consumption
- WordTraceId: 304973
- atomic: true
- Legal Obligation: unknown
- implement: true
- implementerEnhanced: Track Condition
  Change of Allowed Current Consumption
  [LINKED_PHRASE]
- ListNumberText: m)
- kind: ordinary
- KnownTermLink -> 3.12.1.5.a

###### A.3.4.1.4.2.n (Requirement Type)
Revocation of Emergency Stop (Conditional or Unconditional)
- WordTraceId: 305027
- atomic: true
- Legal Obligation: unknown
- implement: true
- ListNumberText: n)
- kind: ordinary

###### A.3.4.1.4.2.o (Requirement Type)
Temporary Speed Restriction Revocation
- WordTraceId: 305087
- atomic: true
- Legal Obligation: unknown
- implement: true
- ListNumberText: o)
- kind: ordinary

###### A.3.4.1.4.2.p (Requirement Type)
Initiation of communication session
- WordTraceId: 305126
- atomic: true
- Legal Obligation: unknown
- implement: true
- ListNumberText: p)
- kind: ordinary

###### A.3.4.1.4.2.q (Requirement Type)
Acknowledgement of session termination
- WordTraceId: 305162
- atomic: true
- Legal Obligation: unknown
- implement: true
- ListNumberText: q)
- kind: ordinary

###### A.3.4.1.4.2.r (Requirement Type)
Default Balise Information
- WordTraceId: 305201
- atomic: true
- Legal Obligation: unknown
- implement: true
- implementerEnhanced: Default
  Balise
  [EXTERNAL]
  Information
  [LINKED_PHRASE]
- ListNumberText: r)
- kind: ordinary
- KnownTermLink -> 3.16.2.4.8

###### A.3.4.1.4.2.s (Requirement Type)
Co-operative shortening of MA (if this message is used, it replaces the movement authority)
- WordTraceId: 305228
- atomic: true
- Legal Obligation: unknown
- implement: true
- implementerEnhanced: Co-operative shortening of MA (
  if
  [CONDITION]
  this message is used, it replaces the movement authority)
- ListNumberText: s)
- kind: ordinary

###### A.3.4.1.4.2.t (Requirement Type)
Train Rejected
- WordTraceId: 305320
- atomic: true
- Legal Obligation: unknown
- implement: true
- ListNumberText: t)
- kind: ordinary

###### A.3.4.1.4.2.u (Requirement Type)
Train Accepted
- WordTraceId: 305335
- atomic: true
- Legal Obligation: unknown
- implement: true
- ListNumberText: u)
- kind: ordinary

###### A.3.4.1.4.2.v (Requirement Type)
SoM position report confirmed by RBC
- WordTraceId: 305350
- atomic: true
- Legal Obligation: unknown
- implement: true
- implementerEnhanced: SoM position report confirmed by
  RBC
  [EXTERNAL]
- ListNumberText: v)
- kind: ordinary

###### A.3.4.1.4.2.w (Requirement Type)
Track Ahead Free up to level 2/3 transition location
- WordTraceId: 305387
- atomic: true
- Legal Obligation: unknown
- implement: true
- implementerEnhanced: Track Ahead Free up to level 2/3 transition location
  [LINKED_PHRASE]
- ListNumberText: w)
- kind: ordinary
- KnownTermLink -> 3.8.2.7.1

###### A.3.4.1.4.2.x (Requirement Type)
Signalling related speed restriction value zero (i.e., train trip order)
- WordTraceId: 305440
- atomic: true
- Legal Obligation: unknown
- implement: true
- ListNumberText: x)
- kind: ordinary

###### A.3.4.1.4.2.y (Requirement Type)
Stop if in SR mode
- WordTraceId: 305513
- atomic: true
- Legal Obligation: unknown
- implement: true
- implementerEnhanced: Stop
  if
  [CONDITION]
  in SR mode
- ListNumberText: y)
- kind: ordinary

###### A.3.4.1.4.2.z (Requirement Type)
Data to be forwarded to a National System through the STM interface
- WordTraceId: 305532
- atomic: true
- Legal Obligation: unknown
- implement: true
- implementerEnhanced: Data to be forwarded to a
  National System
  [EXTERNAL]
  [LINKED_PHRASE]
  through the STM interface
- ListNumberText: z)
- kind: ordinary
- KnownTermLink -> 3.15.6.5.1

#### A.3.5 (Requirement Type)
A.3.5 Handling of Actions in Specific Situations
- WordTraceId: 305600
- atomic: false
- Legal Obligation: not applicable
- PlainText: Handling of Actions in Specific Situations
- implement: false
- kind: Heading

##### A.3.5.1 (Requirement Type)
A.3.5.1 Regards actions executed in reference to location information received from trackside, the on-board equipment shall ensure that the action related to a location is neither reverted, nor executed twice. Situations to be considered shall include reverse movement (initiated by driver or due to roll-away) and the sub-sequent forward movement, or adjustment of train position on passing a new LRBG. This rule shall apply to the following actions:
- WordTraceId: 305649
- atomic: false
- Legal Obligation: not applicable
- PlainText: Regards actions executed in reference to location information received from trackside, the on-board equipment shall ensure that the action related to a location is neither reverted, nor executed twice. Situations to be considered shall include reverse movement (initiated by driver or due to roll-away) and the sub-sequent forward movement, or adjustment of train position on passing a new LRBG. This rule shall apply to the following actions:
- implement: false
- implementerEnhanced: Regards actions executed in reference to location information received from
  trackside
  [EXTERNAL]
  , the
  on-board equipment
  [SELF]
  shall ensure that the action related to a location is neither reverted, nor executed twice. Situations to be considered shall include reverse movement (initiated by
  driver
  [EXTERNAL]
  or due to roll-away) and the sub-sequent forward movement, or adjustment of train position on passing a new
  LRBG
  [EXTERNAL]
  . This rule shall apply to the following actions:
- kind: Heading

###### A.3.5.1.*[1] (Requirement Type)
Change of National Values (see 3.18.2)
- WordTraceId: 306101
- atomic: true
- Legal Obligation: mandatory
- implement: true
- ListNumberText: ·
- kind: ordinary
- CrossRefLink -> 3.18.2

###### A.3.5.1.*[2] (Requirement Type)
Request to acknowledge new level, level transition (see SRS chapter 5.10)
- WordTraceId: 306140
- atomic: true
- Legal Obligation: mandatory
- implement: true
- ListNumberText: ·
- kind: ordinary
- CrossRefLink -> 5.10

###### A.3.5.1.*[3] (Requirement Type)
Start and stop displaying plain or fixed text messages (see 3.12.3)
- WordTraceId: 306214
- atomic: true
- Legal Obligation: mandatory
- implement: true
- ListNumberText: ·
- kind: ordinary
- CrossRefLink -> 3.12.3

###### A.3.5.1.*[4] (Requirement Type)
Request to acknowledge a mode profile, mode transition due to mode profile (see 3.12.4)
- WordTraceId: 306282
- atomic: true
- Legal Obligation: mandatory
- implement: true
- ListNumberText: ·
- kind: ordinary
- CrossRefLink -> 3.12.4

###### A.3.5.1.*[5] (Requirement Type)
Start and stop accepting radio infill information (see 3.9.3)
- WordTraceId: 306370
- atomic: true
- Legal Obligation: mandatory
- implement: true
- ListNumberText: ·
- kind: ordinary
- CrossRefLink -> 3.9.3

###### A.3.5.1.*[6] (Requirement Type)
Actions related to RBC/RBC handover (see 3.15.1)
- WordTraceId: 306432
- atomic: true
- Legal Obligation: mandatory
- implement: true
- implementerEnhanced: Actions related to
  RBC
  [EXTERNAL]
  /
  RBC
  [EXTERNAL]
  handover (see 3.15.1)
- ListNumberText: ·
- kind: ordinary
- CrossRefLink -> 3.15.1

###### A.3.5.1.*[7] (Requirement Type)
Actions related to track condition information (see 3.12.1) with the exception of big metal masses
- WordTraceId: 306481
- atomic: true
- Legal Obligation: mandatory
- implement: true
- implementerEnhanced: Actions related to track condition information (see 3.12.1) with the exception of
  big metal masses
  [LINKED_PHRASE]
- ListNumberText: ·
- kind: ordinary
- CrossRefLink -> 3.12.1
- KnownTermLink -> 3.12.1.5.a

###### A.3.5.1.*[8] (Requirement Type)
Permission to initiate Reversing mode, i.e., limits of Reversing Area (see 3.15.4)
- WordTraceId: 306580
- atomic: true
- Legal Obligation: mandatory
- implement: true
- ListNumberText: ·
- kind: ordinary
- CrossRefLink -> 3.15.4

###### A.3.5.1.*[9] (Requirement Type)
Start and stop Track Ahead free request to driver (see 3.15.5)”
- WordTraceId: 306663
- atomic: true
- Legal Obligation: mandatory
- implement: true
- implementerEnhanced: Start and stop Track Ahead free request to
  driver
  [EXTERNAL]
  (see 3.15.5)”
- ListNumberText: ·
- kind: ordinary
- CrossRefLink -> 3.15.5

###### A.3.5.1.*[10] (Requirement Type)
Start and stop calculation of geographical position (see 3.6.6)
- WordTraceId: 306727
- atomic: true
- Legal Obligation: mandatory
- implement: true
- ListNumberText: ·
- kind: ordinary
- CrossRefLink -> 3.6.6

##### A.3.5.2 (Requirement Type)
A.3.5.2 Once the ERTMS/ETCS on-board equipment has received a balise group message (i.e. once it has received the last balise telegram of the balise group), the action(s) resulting from its content shall take into account the train position measured at the time of reception of this last telegram and shall take precedence on any other action related to a further location that is reached before the message has been fully processed.
- WordTraceId: 306791
- atomic: false
- Legal Obligation: mandatory
- PlainText: Once the ERTMS/ETCS on-board equipment has received a balise group message (i.e. once it has received the last balise telegram of the balise group), the action(s) resulting from its content shall take into account the train position measured at the time of reception of this last telegram and shall take precedence on any other action related to a further location that is reached before the message has been fully processed.
- implement: true
- implementerEnhanced: Once the
  ERTMS/ETCS on-board equipment
  [SELF]
  has received a
  balise group
  [EXTERNAL]
  message (i.e. once it has received the last balise telegram of the
  balise group
  [EXTERNAL]
  ), the action(s) resulting from its content shall take into account the train position measured at the
  time
  [TIME]
  of reception of this last telegram and shall take precedence on any other action related to a further location that is reached before the message has been fully processed.
- kind: ordinary

###### A.3.5.2.1 (Requirement Type)
A.3.5.2.1 Example 1: in level 1, the crossing of the EOA/LOA location with the min safe antenna, before a new extended MA (received when the min safe antenna was in rear of the EOA/LOA) has been processed, will not lead to train trip. In other terms the replacement of the EOA/LOA is considered by the on-board as happening before the min safe antenna crosses the EOA/LOA location (i.e. preventing that clause 3.13.10.2.7 applies).
- WordTraceId: 307225
- atomic: false
- Legal Obligation: not applicable
- PlainText: Example 1: in level 1, the crossing of the EOA/LOA location with the min safe antenna, before a new extended MA (received when the min safe antenna was in rear of the EOA/LOA) has been processed, will not lead to train trip. In other terms the replacement of the EOA/LOA is considered by the on-board as happening before the min safe antenna crosses the EOA/LOA location (i.e. preventing that clause 3.13.10.2.7 applies).
- implement: false
- implementerEnhanced: Example 1: in level 1, the crossing of the EOA/LOA location with the min safe antenna, before a new extended MA (received
  when
  [CONDITION]
  the min safe antenna was in rear of the EOA/LOA) has been processed, will not lead to train trip. In other terms the replacement of the EOA/LOA is considered by the on-board as happening before the min safe antenna crosses the EOA/LOA location (i.e. preventing that clause 3.13.10.2.7 applies).
- kind: Example
- CrossRefLink -> 3.13.10.2.7

###### A.3.5.2.2 (Requirement Type)
A.3.5.2.2 Example 2: when the override function is active, the crossing of the former EOA location by the min safe antenna, before a “Stop if in SR” information (received when the min safe antenna was in rear of the former EOA) has been processed, will not lead to the end of the override procedure followed by a train trip due to “Stop if in SR”. In other terms, both the deletion of the former EOA and the end of override procedure (see 5.8.3.1.3 and 5.8.4.1 c)) are considered by the on-board as simultaneously happening before the min safe antenna crosses the former EOA/LOA location.
- WordTraceId: 307657
- atomic: false
- Legal Obligation: not applicable
- PlainText: Example 2: when the override function is active, the crossing of the former EOA location by the min safe antenna, before a “Stop if in SR” information (received when the min safe antenna was in rear of the former EOA) has been processed, will not lead to the end of the override procedure followed by a train trip due to “Stop if in SR”. In other terms, both the deletion of the former EOA and the end of override procedure (see 5.8.3.1.3 and 5.8.4.1 c)) are considered by the on-board as simultaneously happening before the min safe antenna crosses the former EOA/LOA location.
- implement: false
- implementerEnhanced: Example 2:
  when
  [CONDITION]
  the override function is active, the crossing of the former EOA location by the min safe antenna, before a “Stop
  if
  [CONDITION]
  in SR” information (received
  when
  [CONDITION]
  the min safe antenna was in rear of the former EOA) has been processed, will not lead to the end of the override procedure followed by a train trip due to “Stop
  if
  [CONDITION]
  in SR”. In other terms, both the deletion of the former EOA and the end of override procedure (see 5.8.3.1.3 and 5.8.4.1 c)) are considered by the on-board as simultaneously happening before the min safe antenna crosses the former EOA/LOA location.
- kind: Example
- CrossRefLink -> 5.8.3.1.3
- CrossRefLink -> 5.8.4.1.c

#### A.3.6 (Requirement Type)
A.3.6 Deletion of accepted and stored information when used
- WordTraceId: 308246
- atomic: false
- Legal Obligation: not applicable
- PlainText: Deletion of accepted and stored information when used
- implement: false
- implementerEnhanced: Deletion of accepted and stored information
  when
  [CONDITION]
  used
- kind: Heading

##### A.3.6.1 (Requirement Type)
A3.6.1 Standard case
- WordTraceId: 308306
- atomic: false
- Legal Obligation: not applicable
- PlainText: Standard case
- implement: false
- implementerEnhanced: Standard case
- kind: Heading

###### A.3.6.1.1 (Requirement Type)
A3.6.1.1 When the train moves in the direction of its train orientation, storage capacity occupied by trackside information no longer used, i.e., the related on-board functionality has been completed, shall be made available immediately.
- WordTraceId: 308327
- atomic: true
- Legal Obligation: mandatory
- PlainText: When the train moves in the direction of its train orientation, storage capacity occupied by trackside information no longer used, i.e., the related on-board functionality has been completed, shall be made available immediately.
- implement: true
- implementerEnhanced: When
  [CONDITION]
  the train moves in the direction of its train orientation, storage capacity occupied by
  trackside
  [EXTERNAL]
  information no longer used, i.e., the related on-board functionality has been completed, shall be made available
  immediately
  [WEAK]
  .
- kind: ordinary

###### A.3.6.1.1.1 (Requirement Type)
A3.6.1.1.1 Note: The requirement is needed to allow trackside to predict the storage capacity available on-board in order to comply with dimensioning rules regards information stored on-board given in Subset 040.
- WordTraceId: 308565
- atomic: false
- Legal Obligation: not applicable
- PlainText: Note: The requirement is needed to allow trackside to predict the storage capacity available on-board in order to comply with dimensioning rules regards information stored on-board given in Subset 040.
- implement: false
- implementerEnhanced: Note: The requirement is needed to allow
  trackside
  [EXTERNAL]
  to predict the storage capacity available on-board in order to comply with dimensioning rules regards information stored on-board given in Subset 040.
- kind: Note

##### A.3.6.2 (Requirement Type)
A3.6.2 Exception
- WordTraceId: 308778
- atomic: false
- Legal Obligation: not applicable
- PlainText: Exception
- implement: false
- implementerEnhanced: Exception
- kind: Heading

###### A.3.6.2.1 (Requirement Type)
A3.6.2.1 Following information shall remain stored on-board for a distance defined by a fixed value in rear of the min safe rear end position of the train:
- WordTraceId: 308795
- atomic: true
- Legal Obligation: mandatory
- PlainText: Following information shall remain stored on-board for a distance defined by a fixed value in rear of the min safe rear end position of the train:
- implement: true
- kind: ordinary

###### A.3.6.2.1.*[1] (Requirement Type)
location dependent static speed restrictions , i.e., SSP, ASP, TSR, LX SR, PBD SR (see 3.11.2.2)
- WordTraceId: 308951
- atomic: true
- Legal Obligation: unknown
- implement: true
- ListNumberText: ·
- kind: ordinary
- CrossRefLink -> 3.11.2.2

###### A.3.6.2.1.*[2] (Requirement Type)
gradient information,
- WordTraceId: 309048
- atomic: true
- Legal Obligation: unknown
- implement: true
- ListNumberText: ·
- kind: ordinary

###### A.3.6.2.1.*[3] (Requirement Type)
reduced adhesion information received from trackside,
- WordTraceId: 309070
- atomic: true
- Legal Obligation: unknown
- implement: true
- implementerEnhanced: reduced adhesion information received from
  trackside
  [EXTERNAL]
  ,
- ListNumberText: ·
- kind: ordinary

###### A.3.6.2.1.*[4] (Requirement Type)
Track condition “Big metal masses”.
- WordTraceId: 309124
- atomic: true
- Legal Obligation: unknown
- implement: true
- implementerEnhanced: Track condition “
  Big metal masses
  [LINKED_PHRASE]
  ”.
- ListNumberText: ·
- kind: ordinary
- KnownTermLink -> 3.12.1.5.a

###### A.3.6.2.1.1 (Requirement Type)
A3.6.2.1.1 Note: The above information remains stored for the case of a reverse movement:
- WordTraceId: 309160
- atomic: false
- Legal Obligation: not applicable
- PlainText: Note: The above information remains stored for the case of a reverse movement:
- implement: false
- implementerEnhanced: Note: The
  above
  [WEAK]
  information remains stored for the case of a reverse movement:
- kind: Note

###### A.3.6.2.1.*[5] (Requirement Type)
With the exception of the track condition “Big metal masses”, the stored information allows the ERTMS/ETCS on-board equipment to calculate speed supervision limits after a reverse movement (roll-away, or initiated by the driver)
- WordTraceId: 309250
- atomic: true
- Legal Obligation: unknown
- implement: true
- implementerEnhanced: With the exception of the track condition “
  Big metal masses
  [LINKED_PHRASE]
  ”, the stored information allows the
  ERTMS/ETCS on-board equipment
  [SELF]
  to calculate speed supervision limits
  after
  [TIME]
  a reverse movement (roll-away, or initiated by the
  driver
  [EXTERNAL]
  )
- ListNumberText: ·
- kind: ordinary
- KnownTermLink -> 3.12.1.5.a

###### A.3.6.2.1.*[6] (Requirement Type)
Track condition “Big metal masses” is needed also for a reverse movement itself to avoid any false alarms due to Big metal masses in the track.
- WordTraceId: 309481
- atomic: true
- Legal Obligation: unknown
- implement: true
- implementerEnhanced: Track condition “
  Big metal masses
  [LINKED_PHRASE]
  ” is needed also for a reverse movement itself to avoid any false alarms due to
  Big
  [LINKED_PHRASE]
  metal masses
  [LINKED_PHRASE]
  in the track
  [LINKED_PHRASE]
  .
- ListNumberText: ·
- kind: ordinary
- KnownTermLink -> 3.15.7.1
- KnownTermLink -> 3.12.1.5.a

###### A.3.6.2.1.2 (Requirement Type)
A3.6.2.1.2 Note: The distance to intervention of the roll away or reverse movement supervision is determined by a National/Default value. This is also true for a reverse movement in Post trip mode. However, following an intervention, the train will not stop immediately. In order to keep the on-board functionality simple, a fixed distance value was chosen to define an unambiguous location in rear of the train where the above information is no longer required and the related on-board storage capacity is made available again.
- WordTraceId: 309625
- atomic: false
- Legal Obligation: not applicable
- PlainText: Note: The distance to intervention of the roll away or reverse movement supervision is determined by a National/Default value.  This is also true for a reverse movement in Post trip mode. However, following an intervention, the train will not stop immediately. In order to keep the on-board functionality simple, a fixed distance value was chosen to define an unambiguous location in rear of the train where the above information is no longer required and the related on-board storage capacity is made available again.
- implement: false
- implementerEnhanced: Note: The distance to intervention of the roll away or reverse movement supervision is determined by a National/Default value. This is also true for a reverse movement in Post trip mode. However, following an intervention, the train will not stop
  immediately
  [WEAK]
  . In order to keep the on-board functionality simple, a fixed distance value was chosen to define an unambiguous location in rear of the train where the
  above
  [WEAK]
  information is no longer required and the related on-board storage capacity is made available
  again
  [LOOP]
  .
- kind: Note

#### A.3.7 (Requirement Type)
A.3.7 Calculation of the basic deceleration
- WordTraceId: 310155
- atomic: false
- Legal Obligation: not applicable
- PlainText: Calculation of the basic deceleration
- implement: false
- implementerEnhanced: Calculation of the basic deceleration
- kind: Heading

##### A.3.7.1 (Requirement Type)
A.3.7.1 The brake percentage (λ) shall be converted into two different input parameters:
- WordTraceId: 310200
- atomic: true
- Legal Obligation: mandatory
- PlainText: The brake percentage (λ) shall be converted into two different input parameters:
- implement: true
- kind: ordinary

##### A.3.7.1[2] (Requirement Type)
λ o = λ for calculation of emergency brake deceleration (A_brake_emergency(V))
- WordTraceId: 310289
- atomic: true
- Legal Obligation: unknown
- PlainText: λo = λ for calculation of emergency brake deceleration (A_brake_emergency(V))
- implement: true
- kind: ordinary

##### A.3.7.1[3] (Requirement Type)
λ o = MIN (λ, 135) for calculation of service brake deceleration (A_brake_service(V))
- WordTraceId: 310367
- atomic: true
- Legal Obligation: unknown
- PlainText: λo = MIN (λ, 135) for calculation of service brake deceleration (A_brake_service(V))
- implement: true
- kind: ordinary

##### A.3.7.1[4] (Requirement Type)
where λ is the brake percentage defined as part of Train Data.
- WordTraceId: 310452
- atomic: true
- Legal Obligation: unknown
- implement: true
- kind: ordinary

##### A.3.7.2 (Requirement Type)
A.3.7.2 The calculation of the basic deceleration (A_basic(V)) shall use a common algorithm that will be used twice, once for the service brake and once for the emergency brake.
- WordTraceId: 310515
- atomic: true
- Legal Obligation: mandatory
- PlainText: The calculation of the basic deceleration (A_basic(V)) shall use a common algorithm that will be used twice, once for the service brake and once for the emergency brake.
- implement: true
- kind: ordinary

##### A.3.7.3 (Requirement Type)
A.3.7.3 The speed limit for the first step shall be calculated as V_lim = x * λ
o
y
.
- WordTraceId: 310693
- atomic: true
- Legal Obligation: mandatory
- PlainText: The speed limit for the first step shall be calculated as V_lim = x * λoy.
- implement: true
- kind: ordinary

##### A.3.7.3[2] (Requirement Type)
V_lim is the speed limit for the first step in km/h
- WordTraceId: 310776
- atomic: true
- Legal Obligation: unknown
- implement: true
- kind: ordinary

##### A.3.7.3[3] (Requirement Type)
x = 16.85
- WordTraceId: 310828
- atomic: true
- Legal Obligation: unknown
- implement: true
- kind: ordinary

##### A.3.7.3[4] (Requirement Type)
y = 0.428
- WordTraceId: 310838
- atomic: true
- Legal Obligation: unknown
- implement: true
- kind: ordinary

##### A.3.7.4 (Requirement Type)
A.3.7.4 The first step of the basic deceleration shall be calculated as AD_0 = A * λ
o
+ B
- WordTraceId: 310848
- atomic: true
- Legal Obligation: mandatory
- PlainText: The first step of the basic deceleration shall be calculated as AD_0 = A * λo + B
- implement: true
- kind: ordinary

##### A.3.7.4[2] (Requirement Type)
AD_0 is the basic deceleration in m/s 2 for 0 ≤ speed ≤ V_lim.
- WordTraceId: 310938
- atomic: true
- Legal Obligation: unknown
- PlainText: AD_0 is the basic deceleration in m/s2 for 0 ≤ speed ≤ V_lim.
- implement: true
- kind: ordinary

##### A.3.7.4[3] (Requirement Type)
A = 0.0075
- WordTraceId: 311000
- atomic: true
- Legal Obligation: unknown
- implement: true
- kind: ordinary

##### A.3.7.4[4] (Requirement Type)
B = 0.076
- WordTraceId: 311011
- atomic: true
- Legal Obligation: unknown
- implement: true
- kind: ordinary

##### A.3.7.5 (Requirement Type)
A.3.7.5 The following steps of the basic deceleration shall be calculated by means of a set of polynomials of the third order with the following format:
- WordTraceId: 311021
- atomic: true
- Legal Obligation: mandatory
- PlainText: The following steps of the basic deceleration shall be calculated by means of a set of polynomials of the third order with the following format:
- implement: true
- kind: ordinary

##### A.3.7.5[2] (Requirement Type)
AD_n = a3_n * λ o 3 + a2_n * λ o 2 + a1_n * λ o + a0_n
- WordTraceId: 311174
- atomic: true
- Legal Obligation: unknown
- PlainText: AD_n = a3_n * λo3 + a2_n * λo2 + a1_n * λo + a0_n
- implement: true
- kind: ordinary

##### A.3.7.5[3] (Requirement Type)
and with the following values for n (all speed limits in km/h):
- WordTraceId: 311224
- atomic: true
- Legal Obligation: unknown
- implement: true
- kind: ordinary

##### A.3.7.5[4] (Requirement Type)
n = 1 valid for V_lim < speed ≤ 100 if V_lim ≤ 100
- WordTraceId: 311288
- atomic: true
- Legal Obligation: unknown
- implement: true
- implementerEnhanced: n = 1 valid for V_lim < speed ≤ 100
  if
  [CONDITION]
  V_lim ≤ 100
- kind: ordinary

##### A.3.7.5[5] (Requirement Type)
to be ignored if V_lim > 100
- WordTraceId: 311342
- atomic: true
- Legal Obligation: unknown
- PlainText: to be ignored       if V_lim > 100
- implement: true
- implementerEnhanced: to be ignored
  if
  [CONDITION]
  V_lim > 100
- kind: ordinary

##### A.3.7.5[6] (Requirement Type)
n = 2 valid for V_lim < speed ≤ 120 if 100 < V_lim ≤ 120
- WordTraceId: 311377
- atomic: true
- Legal Obligation: unknown
- implement: true
- implementerEnhanced: n = 2 valid for V_lim < speed ≤ 120
  if
  [CONDITION]
  100 < V_lim ≤ 120
- kind: ordinary

##### A.3.7.5[7] (Requirement Type)
valid for 100 < speed ≤ 120 if V_lim ≤ 100
- WordTraceId: 311437
- atomic: true
- Legal Obligation: unknown
- implement: true
- implementerEnhanced: valid for 100 < speed ≤ 120
  if
  [CONDITION]
  V_lim ≤ 100
- kind: ordinary

##### A.3.7.5[8] (Requirement Type)
to be ignored if V_lim > 120
- WordTraceId: 311481
- atomic: true
- Legal Obligation: unknown
- PlainText: to be ignored       if V_lim > 120
- implement: true
- implementerEnhanced: to be ignored
  if
  [CONDITION]
  V_lim > 120
- kind: ordinary

##### A.3.7.5[9] (Requirement Type)
n = 3 valid for V_lim < speed ≤ 150 if 120 < V_lim ≤ 150
- WordTraceId: 311516
- atomic: true
- Legal Obligation: unknown
- implement: true
- implementerEnhanced: n = 3 valid for V_lim < speed ≤ 150
  if
  [CONDITION]
  120 < V_lim ≤ 150
- kind: ordinary

##### A.3.7.5[10] (Requirement Type)
valid for 120 < speed ≤ 150 if V_lim ≤ 120
- WordTraceId: 311576
- atomic: true
- Legal Obligation: unknown
- implement: true
- implementerEnhanced: valid for 120 < speed ≤ 150
  if
  [CONDITION]
  V_lim ≤ 120
- kind: ordinary

##### A.3.7.5[11] (Requirement Type)
to be ignored if V_lim > 150
- WordTraceId: 311620
- atomic: true
- Legal Obligation: unknown
- PlainText: to be ignored       if V_lim > 150
- implement: true
- implementerEnhanced: to be ignored
  if
  [CONDITION]
  V_lim > 150
- kind: ordinary

##### A.3.7.5[12] (Requirement Type)
n = 4 valid for V_lim < speed ≤ 180 if 150 < V_lim ≤ 180
- WordTraceId: 311655
- atomic: true
- Legal Obligation: unknown
- implement: true
- implementerEnhanced: n = 4 valid for V_lim < speed ≤ 180
  if
  [CONDITION]
  150 < V_lim ≤ 180
- kind: ordinary

##### A.3.7.5[13] (Requirement Type)
valid for 150 < speed ≤ 180 if V_lim ≤ 150
- WordTraceId: 311715
- atomic: true
- Legal Obligation: unknown
- implement: true
- implementerEnhanced: valid for 150 < speed ≤ 180
  if
  [CONDITION]
  V_lim ≤ 150
- kind: ordinary

##### A.3.7.5[14] (Requirement Type)
to be ignored if V_lim > 180
- WordTraceId: 311759
- atomic: true
- Legal Obligation: unknown
- PlainText: to be ignored       if V_lim > 180
- implement: true
- implementerEnhanced: to be ignored
  if
  [CONDITION]
  V_lim > 180
- kind: ordinary

##### A.3.7.5[15] (Requirement Type)
n = 5 valid for V_lim < speed if V_lim > 180
- WordTraceId: 311794
- atomic: true
- Legal Obligation: unknown
- implement: true
- implementerEnhanced: n = 5 valid for V_lim < speed
  if
  [CONDITION]
  V_lim > 180
- kind: ordinary

##### A.3.7.5[16] (Requirement Type)
valid for 180 < speed if V_lim ≤ 180
- WordTraceId: 311844
- atomic: true
- Legal Obligation: unknown
- PlainText: valid for 180 < speed  if V_lim ≤ 180
- implement: true
- implementerEnhanced: valid for 180 < speed
  if
  [CONDITION]
  V_lim ≤ 180
- kind: ordinary

##### A.3.7.6 (Requirement Type)
A.3.7.6 The coefficients for the polynomials shall be defined as follows:
- WordTraceId: 311882
- atomic: true
- Legal Obligation: mandatory
- PlainText: The coefficients for the polynomials shall be defined as follows:
- implement: false
- kind: Definition

##### A.3.7.6[2] (Requirement Type)
- WordTraceId: 311956
- atomic: false
- Legal Obligation: not applicable
- implement: false
- kind: Placeholder

###### A.3.7.6[2].[t]* (Requirement Type)
| [r][1].[c][1] am_n | [r][1].[c][2] | [r][1].[c][3] | [r][1].[c][4] m = | [r][1].[c][5] | [r][1].[c][6] |
| --- | --- | --- | --- | --- | --- |
| [r][2].[c][1] | [r][2].[c][2] | [r][2].[c][3] 3 | [r][2].[c][4] 2 | [r][2].[c][5] 1 | [r][2].[c][6] 0 |
| [r][3].[c][1] | [r][3].[c][2] 1 | [r][3].[c][3] -6.30E-07 | [r][3].[c][4] 6.10E-05 | [r][3].[c][5] 4.72E-03 | [r][3].[c][6] 0.0663 |
| [r][4].[c][1] | [r][4].[c][2] 2 | [r][4].[c][3] 2.73E-07 | [r][4].[c][4] -4.54E-06 | [r][4].[c][5] 5.14E-03 | [r][4].[c][6] 0.1300 |
| [r][5].[c][1] n = | [r][5].[c][2] 3 | [r][5].[c][3] 5.58E-08 | [r][5].[c][4] -6.76E-06 | [r][5].[c][5] 5.81E-03 | [r][5].[c][6] 0.0479 |
| [r][6].[c][1] | [r][6].[c][2] 4 | [r][6].[c][3] 3.00E-08 | [r][6].[c][4] -3.85E-06 | [r][6].[c][5] 5.52E-03 | [r][6].[c][6] 0.0480 |
| [r][7].[c][1] | [r][7].[c][2] 5 | [r][7].[c][3] 3.23E-09 | [r][7].[c][4] 1.66E-06 | [r][7].[c][5] 5.06E-03 | [r][7].[c][6] 0.0559 |
- WordTraceId: 312178
- atomic: false
- Legal Obligation: not applicable
- implement: false
- kind: Table

###### A.3.7.6[2].[t]*.[r][1] (Requirement Type)
- WordTraceId: 311956
- atomic: false
- Legal Obligation: not applicable
- implement: false
- kind: Table

###### A.3.7.6[2].[t]*.[r][1].[c][1] (Requirement Type)
am_n
- WordTraceId: 311956
- atomic: true
- Legal Obligation: unknown
- implement: true
- kind: ordinary

###### A.3.7.6[2].[t]*.[r][1].[c][2] (Requirement Type)
- WordTraceId: 311961
- atomic: true
- Legal Obligation: unknown
- implement: true
- kind: ordinary

###### A.3.7.6[2].[t]*.[r][1].[c][3] (Requirement Type)
- WordTraceId: 311962
- atomic: true
- Legal Obligation: unknown
- implement: true
- kind: ordinary

###### A.3.7.6[2].[t]*.[r][1].[c][4] (Requirement Type)
m =
- WordTraceId: 311963
- atomic: true
- Legal Obligation: unknown
- implement: true
- kind: ordinary

###### A.3.7.6[2].[t]*.[r][1].[c][5] (Requirement Type)
- WordTraceId: 311967
- atomic: true
- Legal Obligation: unknown
- implement: true
- kind: ordinary

###### A.3.7.6[2].[t]*.[r][1].[c][6] (Requirement Type)
- WordTraceId: 311968
- atomic: true
- Legal Obligation: unknown
- implement: true
- kind: ordinary

###### A.3.7.6[2].[t]*.[r][2] (Requirement Type)
- WordTraceId: 311970
- atomic: false
- Legal Obligation: not applicable
- implement: false
- kind: Table

###### A.3.7.6[2].[t]*.[r][2].[c][1] (Requirement Type)
- WordTraceId: 311970
- atomic: true
- Legal Obligation: unknown
- implement: true
- kind: ordinary

###### A.3.7.6[2].[t]*.[r][2].[c][2] (Requirement Type)
- WordTraceId: 311971
- atomic: true
- Legal Obligation: unknown
- implement: true
- kind: ordinary

###### A.3.7.6[2].[t]*.[r][2].[c][3] (Requirement Type)
3
- WordTraceId: 311972
- atomic: true
- Legal Obligation: unknown
- implement: true
- kind: ordinary

###### A.3.7.6[2].[t]*.[r][2].[c][4] (Requirement Type)
2
- WordTraceId: 311974
- atomic: true
- Legal Obligation: unknown
- implement: true
- kind: ordinary

###### A.3.7.6[2].[t]*.[r][2].[c][5] (Requirement Type)
1
- WordTraceId: 311976
- atomic: true
- Legal Obligation: unknown
- implement: true
- kind: ordinary

###### A.3.7.6[2].[t]*.[r][2].[c][6] (Requirement Type)
0
- WordTraceId: 311978
- atomic: true
- Legal Obligation: unknown
- implement: true
- kind: ordinary

###### A.3.7.6[2].[t]*.[r][3] (Requirement Type)
- WordTraceId: 311981
- atomic: false
- Legal Obligation: not applicable
- implement: false
- kind: Table

###### A.3.7.6[2].[t]*.[r][3].[c][1] (Requirement Type)
- WordTraceId: 311981
- atomic: true
- Legal Obligation: unknown
- implement: true
- kind: ordinary

###### A.3.7.6[2].[t]*.[r][3].[c][2] (Requirement Type)
1
- WordTraceId: 311982
- atomic: true
- Legal Obligation: unknown
- implement: true
- kind: ordinary

###### A.3.7.6[2].[t]*.[r][3].[c][3] (Requirement Type)
-6.30E-07
- WordTraceId: 311984
- atomic: true
- Legal Obligation: unknown
- implement: true
- kind: ordinary

###### A.3.7.6[2].[t]*.[r][3].[c][4] (Requirement Type)
6.10E-05
- WordTraceId: 311994
- atomic: true
- Legal Obligation: unknown
- implement: true
- kind: ordinary

###### A.3.7.6[2].[t]*.[r][3].[c][5] (Requirement Type)
4.72E-03
- WordTraceId: 312003
- atomic: true
- Legal Obligation: unknown
- implement: true
- kind: ordinary

###### A.3.7.6[2].[t]*.[r][3].[c][6] (Requirement Type)
0.0663
- WordTraceId: 312012
- atomic: true
- Legal Obligation: unknown
- implement: true
- kind: ordinary

###### A.3.7.6[2].[t]*.[r][4] (Requirement Type)
- WordTraceId: 312020
- atomic: false
- Legal Obligation: not applicable
- implement: false
- kind: Table

###### A.3.7.6[2].[t]*.[r][4].[c][1] (Requirement Type)
- WordTraceId: 312020
- atomic: true
- Legal Obligation: unknown
- implement: true
- kind: ordinary

###### A.3.7.6[2].[t]*.[r][4].[c][2] (Requirement Type)
2
- WordTraceId: 312021
- atomic: true
- Legal Obligation: unknown
- implement: true
- kind: ordinary

###### A.3.7.6[2].[t]*.[r][4].[c][3] (Requirement Type)
2.73E-07
- WordTraceId: 312023
- atomic: true
- Legal Obligation: unknown
- implement: true
- kind: ordinary

###### A.3.7.6[2].[t]*.[r][4].[c][4] (Requirement Type)
-4.54E-06
- WordTraceId: 312032
- atomic: true
- Legal Obligation: unknown
- implement: true
- kind: ordinary

###### A.3.7.6[2].[t]*.[r][4].[c][5] (Requirement Type)
5.14E-03
- WordTraceId: 312042
- atomic: true
- Legal Obligation: unknown
- implement: true
- kind: ordinary

###### A.3.7.6[2].[t]*.[r][4].[c][6] (Requirement Type)
0.1300
- WordTraceId: 312051
- atomic: true
- Legal Obligation: unknown
- implement: true
- kind: ordinary

###### A.3.7.6[2].[t]*.[r][5] (Requirement Type)
- WordTraceId: 312059
- atomic: false
- Legal Obligation: not applicable
- implement: false
- kind: Table

###### A.3.7.6[2].[t]*.[r][5].[c][1] (Requirement Type)
n =
- WordTraceId: 312059
- atomic: true
- Legal Obligation: unknown
- implement: true
- kind: ordinary

###### A.3.7.6[2].[t]*.[r][5].[c][2] (Requirement Type)
3
- WordTraceId: 312063
- atomic: true
- Legal Obligation: unknown
- implement: true
- kind: ordinary

###### A.3.7.6[2].[t]*.[r][5].[c][3] (Requirement Type)
5.58E-08
- WordTraceId: 312065
- atomic: true
- Legal Obligation: unknown
- implement: true
- kind: ordinary

###### A.3.7.6[2].[t]*.[r][5].[c][4] (Requirement Type)
-6.76E-06
- WordTraceId: 312074
- atomic: true
- Legal Obligation: unknown
- implement: true
- kind: ordinary

###### A.3.7.6[2].[t]*.[r][5].[c][5] (Requirement Type)
5.81E-03
- WordTraceId: 312084
- atomic: true
- Legal Obligation: unknown
- implement: true
- kind: ordinary

###### A.3.7.6[2].[t]*.[r][5].[c][6] (Requirement Type)
0.0479
- WordTraceId: 312093
- atomic: true
- Legal Obligation: unknown
- implement: true
- kind: ordinary

###### A.3.7.6[2].[t]*.[r][6] (Requirement Type)
- WordTraceId: 312101
- atomic: false
- Legal Obligation: not applicable
- implement: false
- kind: Table

###### A.3.7.6[2].[t]*.[r][6].[c][1] (Requirement Type)
- WordTraceId: 312101
- atomic: true
- Legal Obligation: unknown
- implement: true
- kind: ordinary

###### A.3.7.6[2].[t]*.[r][6].[c][2] (Requirement Type)
4
- WordTraceId: 312102
- atomic: true
- Legal Obligation: unknown
- implement: true
- kind: ordinary

###### A.3.7.6[2].[t]*.[r][6].[c][3] (Requirement Type)
3.00E-08
- WordTraceId: 312104
- atomic: true
- Legal Obligation: unknown
- implement: true
- kind: ordinary

###### A.3.7.6[2].[t]*.[r][6].[c][4] (Requirement Type)
-3.85E-06
- WordTraceId: 312113
- atomic: true
- Legal Obligation: unknown
- implement: true
- kind: ordinary

###### A.3.7.6[2].[t]*.[r][6].[c][5] (Requirement Type)
5.52E-03
- WordTraceId: 312123
- atomic: true
- Legal Obligation: unknown
- implement: true
- kind: ordinary

###### A.3.7.6[2].[t]*.[r][6].[c][6] (Requirement Type)
0.0480
- WordTraceId: 312132
- atomic: true
- Legal Obligation: unknown
- implement: true
- kind: ordinary

###### A.3.7.6[2].[t]*.[r][7] (Requirement Type)
- WordTraceId: 312140
- atomic: false
- Legal Obligation: not applicable
- implement: false
- kind: Table

###### A.3.7.6[2].[t]*.[r][7].[c][1] (Requirement Type)
- WordTraceId: 312140
- atomic: true
- Legal Obligation: unknown
- implement: true
- kind: ordinary

###### A.3.7.6[2].[t]*.[r][7].[c][2] (Requirement Type)
5
- WordTraceId: 312141
- atomic: true
- Legal Obligation: unknown
- implement: true
- kind: ordinary

###### A.3.7.6[2].[t]*.[r][7].[c][3] (Requirement Type)
3.23E-09
- WordTraceId: 312143
- atomic: true
- Legal Obligation: unknown
- implement: true
- kind: ordinary

###### A.3.7.6[2].[t]*.[r][7].[c][4] (Requirement Type)
1.66E-06
- WordTraceId: 312152
- atomic: true
- Legal Obligation: unknown
- implement: true
- kind: ordinary

###### A.3.7.6[2].[t]*.[r][7].[c][5] (Requirement Type)
5.06E-03
- WordTraceId: 312161
- atomic: true
- Legal Obligation: unknown
- implement: true
- kind: ordinary

###### A.3.7.6[2].[t]*.[r][7].[c][6] (Requirement Type)
0.0559
- WordTraceId: 312170
- atomic: true
- Legal Obligation: unknown
- implement: true
- kind: ordinary

#### A.3.8 (Requirement Type)
A.3.8 Calculation of the emergency brake equivalent time
- WordTraceId: 312178
- atomic: false
- Legal Obligation: not applicable
- PlainText: Calculation of the emergency brake equivalent time
- implement: false
- implementerEnhanced: Calculation of the emergency brake equivalent
  time
  [TIME]
- kind: Heading

##### A.3.8.1 (Requirement Type)
A.3.8.1 The basic brake build up time for the emergency brake with the brake position in passenger trains in P shall be calculated as:
- WordTraceId: 312235
- atomic: true
- Legal Obligation: mandatory
- PlainText: The basic brake build up time for the emergency brake with the brake position in passenger trains in P shall be calculated as:
- implement: true
- implementerEnhanced: The basic brake build up
  time
  [TIME]
  for the emergency brake with the brake position in passenger trains in P shall be calculated as:
- kind: ordinary

##### A.3.8.1[2] (Requirement Type)
T_brake_basic_eb = a + b * (L/100) + c * (L/100) 2
- WordTraceId: 312370
- atomic: true
- Legal Obligation: unknown
- PlainText: T_brake_basic_eb = a + b * (L/100) + c * (L/100)2
- implement: true
- kind: ordinary

##### A.3.8.1[3] (Requirement Type)
where
- WordTraceId: 312420
- atomic: true
- Legal Obligation: unknown
- implement: true
- kind: ordinary

##### A.3.8.1[4] (Requirement Type)
L = MAX (400m; train length in m)
- WordTraceId: 312426
- atomic: false
- Legal Obligation: unknown
- implement: true
- kind: ordinary

##### A.3.8.1[5] (Requirement Type)
a = 2.30
- WordTraceId: 312460
- atomic: true
- Legal Obligation: unknown
- implement: true
- kind: ordinary

##### A.3.8.1[6] (Requirement Type)
b = 0.00
- WordTraceId: 312469
- atomic: true
- Legal Obligation: unknown
- implement: true
- kind: ordinary

##### A.3.8.1[7] (Requirement Type)
c = 0.17
- WordTraceId: 312478
- atomic: true
- Legal Obligation: unknown
- implement: true
- kind: ordinary

##### A.3.8.2 (Requirement Type)
A.3.8.2 The basic brake build up time for the emergency brake with the brake position in freight trains in P shall be calculated as:
- WordTraceId: 312487
- atomic: true
- Legal Obligation: mandatory
- PlainText: The basic brake build up time for the emergency brake with the brake position in freight trains in P shall be calculated as:
- implement: true
- implementerEnhanced: The basic brake build up
  time
  [TIME]
  for the emergency brake with the brake position in freight trains in P shall be calculated as:
- kind: ordinary

##### A.3.8.2[2] (Requirement Type)
T_brake_basic_eb = a + b * (L/100) + c * (L/100) 2
- WordTraceId: 312620
- atomic: true
- Legal Obligation: unknown
- PlainText: T_brake_basic_eb = a + b * (L/100) + c * (L/100)2
- implement: true
- kind: ordinary

##### A.3.8.2[3] (Requirement Type)
where
- WordTraceId: 312670
- atomic: true
- Legal Obligation: unknown
- implement: true
- kind: ordinary

##### A.3.8.2[4] (Requirement Type)
L = MAX (400m; train length in m)
- WordTraceId: 312676
- atomic: false
- Legal Obligation: unknown
- implement: true
- kind: ordinary

##### A.3.8.2[5] (Requirement Type)
If train length ≤ 900m:
- WordTraceId: 312710
- atomic: true
- Legal Obligation: unknown
- implement: true
- implementerEnhanced: If
  [CONDITION]
  train length ≤ 900m:
- kind: ordinary

##### A.3.8.2[6] (Requirement Type)
a = 2.30
- WordTraceId: 312734
- atomic: true
- Legal Obligation: unknown
- implement: true
- kind: ordinary

##### A.3.8.2[7] (Requirement Type)
b = 0.00
- WordTraceId: 312743
- atomic: true
- Legal Obligation: unknown
- implement: true
- kind: ordinary

##### A.3.8.2[8] (Requirement Type)
c = 0.17
- WordTraceId: 312752
- atomic: true
- Legal Obligation: unknown
- implement: true
- kind: ordinary

##### A.3.8.2[9] (Requirement Type)
If 900m < train length ≤ 1500m:
- WordTraceId: 312761
- atomic: true
- Legal Obligation: unknown
- implement: true
- implementerEnhanced: If
  [CONDITION]
  900m < train length ≤ 1500m:
- kind: ordinary

##### A.3.8.2[10] (Requirement Type)
a = -0.40
- WordTraceId: 312793
- atomic: true
- Legal Obligation: unknown
- implement: true
- kind: ordinary

##### A.3.8.2[11] (Requirement Type)
b = 1.60
- WordTraceId: 312803
- atomic: true
- Legal Obligation: unknown
- implement: true
- kind: ordinary

##### A.3.8.2[12] (Requirement Type)
c = 0.03
- WordTraceId: 312812
- atomic: true
- Legal Obligation: unknown
- implement: true
- kind: ordinary

##### A.3.8.3 (Requirement Type)
A.3.8.3 The basic brake build up time for the emergency brake with the brake position in freight trains in G shall be calculated as:
- WordTraceId: 312821
- atomic: true
- Legal Obligation: mandatory
- PlainText: The basic brake build up time for the emergency brake with the brake position in freight trains in G shall be calculated as:
- implement: true
- implementerEnhanced: The basic brake build up
  time
  [TIME]
  for the emergency brake with the brake position in freight trains in G shall be calculated as:
- kind: ordinary

##### A.3.8.3[2] (Requirement Type)
T_brake_basic_eb = a + b * (L/100) + c * (L/100) 2
- WordTraceId: 312954
- atomic: true
- Legal Obligation: unknown
- PlainText: T_brake_basic_eb = a + b * (L/100) + c * (L/100)2
- implement: true
- kind: ordinary

##### A.3.8.3[3] (Requirement Type)
where
- WordTraceId: 313004
- atomic: true
- Legal Obligation: unknown
- implement: true
- kind: ordinary

##### A.3.8.3[4] (Requirement Type)
L = train length in m
- WordTraceId: 313010
- atomic: true
- Legal Obligation: unknown
- implement: true
- kind: ordinary

##### A.3.8.3[5] (Requirement Type)
If train length ≤ 900m:
- WordTraceId: 313032
- atomic: true
- Legal Obligation: unknown
- implement: true
- implementerEnhanced: If
  [CONDITION]
  train length ≤ 900m:
- kind: ordinary

##### A.3.8.3[6] (Requirement Type)
a = 12.00
- WordTraceId: 313056
- atomic: true
- Legal Obligation: unknown
- implement: true
- kind: ordinary

##### A.3.8.3[7] (Requirement Type)
b = 0.00
- WordTraceId: 313066
- atomic: true
- Legal Obligation: unknown
- implement: true
- kind: ordinary

##### A.3.8.3[8] (Requirement Type)
c = 0.05
- WordTraceId: 313075
- atomic: true
- Legal Obligation: unknown
- implement: true
- kind: ordinary

##### A.3.8.3[9] (Requirement Type)
If 900m < train length ≤ 1500m:
- WordTraceId: 313084
- atomic: true
- Legal Obligation: unknown
- implement: true
- implementerEnhanced: If
  [CONDITION]
  900m < train length ≤ 1500m:
- kind: ordinary

##### A.3.8.3[10] (Requirement Type)
a = -0.40
- WordTraceId: 313116
- atomic: true
- Legal Obligation: unknown
- implement: true
- kind: ordinary

##### A.3.8.3[11] (Requirement Type)
b = 1.60
- WordTraceId: 313126
- atomic: true
- Legal Obligation: unknown
- implement: true
- kind: ordinary

##### A.3.8.3[12] (Requirement Type)
c = 0.03
- WordTraceId: 313135
- atomic: true
- Legal Obligation: unknown
- implement: true
- kind: ordinary

##### A.3.8.4 (Requirement Type)
A.3.8.4 The equivalent brake build up time for the emergency brake shall be computed as follows:
- WordTraceId: 313144
- atomic: true
- Legal Obligation: mandatory
- PlainText: The equivalent brake build up time for the emergency brake shall be computed as follows:
- implement: true
- implementerEnhanced: The equivalent brake build up
  time
  [TIME]
  for the emergency brake shall be computed as follows:
- kind: ordinary

##### A.3.8.4[2] (Requirement Type)
T_brake_emergency_cm0 = T_brake_basic_eb when V_target = 0
- WordTraceId: 313241
- atomic: true
- Legal Obligation: unknown
- implement: true
- implementerEnhanced: T_brake_emergency_cm0 = T_brake_basic_eb
  when
  [CONDITION]
  V_target = 0
- kind: ordinary

##### A.3.8.4[3] (Requirement Type)
T_brake_emergency_cmt = kto * T_brake_basic_eb when V_target > 0
- WordTraceId: 313300
- atomic: true
- Legal Obligation: unknown
- implement: true
- implementerEnhanced: T_brake_emergency_cmt = kto * T_brake_basic_eb
  when
  [CONDITION]
  V_target > 0
- kind: ordinary

##### A.3.8.4[4] (Requirement Type)
where
- WordTraceId: 313365
- atomic: true
- Legal Obligation: unknown
- implement: true
- kind: ordinary

##### A.3.8.4[5] (Requirement Type)
V_target is the target speed
- WordTraceId: 313371
- atomic: true
- Legal Obligation: unknown
- implement: true
- kind: ordinary

##### A.3.8.5 (Requirement Type)
A.3.8.5 The correction factor kto shall depend on the brake position as follows:
- WordTraceId: 313400
- atomic: true
- Legal Obligation: mandatory
- PlainText: The correction factor kto shall depend on the brake position as follows:
- implement: true
- kind: ordinary

##### A.3.8.5[2] (Requirement Type)
kto = 1 + Ct
- WordTraceId: 313481
- atomic: true
- Legal Obligation: unknown
- implement: true
- kind: ordinary

##### A.3.8.5[3] (Requirement Type)
where
- WordTraceId: 313494
- atomic: true
- Legal Obligation: unknown
- implement: true
- kind: ordinary

##### A.3.8.5[4] (Requirement Type)
Ct = 0.16 for freight trains in G
- WordTraceId: 313500
- atomic: true
- Legal Obligation: unknown
- PlainText: Ct = 0.16  for freight trains in G
- implement: true
- kind: ordinary

##### A.3.8.5[5] (Requirement Type)
Ct = 0.20 for freight trains in P
- WordTraceId: 313535
- atomic: true
- Legal Obligation: unknown
- PlainText: Ct = 0.20  for freight trains in P
- implement: true
- kind: ordinary

##### A.3.8.5[6] (Requirement Type)
Ct = 0.20 for passenger trains
- WordTraceId: 313570
- atomic: true
- Legal Obligation: unknown
- PlainText: Ct = 0.20  for passenger trains
- implement: true
- kind: ordinary

#### A.3.9 (Requirement Type)
A.3.9 Calculation of the full service brake equivalent time
- WordTraceId: 313602
- atomic: false
- Legal Obligation: not applicable
- PlainText: Calculation of the full service brake equivalent time
- implement: false
- implementerEnhanced: Calculation of the full service brake equivalent
  time
  [TIME]
- kind: Heading

##### A.3.9.1 (Requirement Type)
A.3.9.1 The basic brake build up time for full service brake for passenger trains in P shall be calculated as:
- WordTraceId: 313662
- atomic: true
- Legal Obligation: mandatory
- PlainText: The basic brake build up time for full service brake for passenger trains in P shall be calculated as:
- implement: true
- implementerEnhanced: The basic brake build up
  time
  [TIME]
  for full service brake for passenger trains in P shall be calculated as:
- kind: ordinary

##### A.3.9.1[2] (Requirement Type)
T_brake_basic_sb = a + b * (L/100) + c * (L/100) 2
- WordTraceId: 313773
- atomic: true
- Legal Obligation: unknown
- PlainText: T_brake_basic_sb = a + b * (L/100) + c * (L/100)2
- implement: true
- kind: ordinary

##### A.3.9.1[3] (Requirement Type)
where
- WordTraceId: 313823
- atomic: true
- Legal Obligation: unknown
- implement: true
- kind: ordinary

##### A.3.9.1[4] (Requirement Type)
L = train length in m
- WordTraceId: 313829
- atomic: true
- Legal Obligation: unknown
- implement: true
- kind: ordinary

##### A.3.9.1[5] (Requirement Type)
a = 3.00
- WordTraceId: 313851
- atomic: true
- Legal Obligation: unknown
- implement: true
- kind: ordinary

##### A.3.9.1[6] (Requirement Type)
b = 1.50
- WordTraceId: 313860
- atomic: true
- Legal Obligation: unknown
- implement: true
- kind: ordinary

##### A.3.9.1[7] (Requirement Type)
c = 0.10
- WordTraceId: 313869
- atomic: true
- Legal Obligation: unknown
- implement: true
- kind: ordinary

##### A.3.9.2 (Requirement Type)
A.3.9.2 The basic brake build up time for full service brake for freight trains in P shall be calculated as:
- WordTraceId: 313878
- atomic: true
- Legal Obligation: mandatory
- PlainText: The basic brake build up time for full service brake for freight trains in P shall be calculated as:
- implement: true
- implementerEnhanced: The basic brake build up
  time
  [TIME]
  for full service brake for freight trains in P shall be calculated as:
- kind: ordinary

##### A.3.9.2[2] (Requirement Type)
T_brake_basic_sb = a + b * (L/100) + c * (L/100) 2
- WordTraceId: 313987
- atomic: true
- Legal Obligation: unknown
- PlainText: T_brake_basic_sb = a + b * (L/100) + c * (L/100)2
- implement: true
- kind: ordinary

##### A.3.9.2[3] (Requirement Type)
where
- WordTraceId: 314037
- atomic: true
- Legal Obligation: unknown
- implement: true
- kind: ordinary

##### A.3.9.2[4] (Requirement Type)
L = train length in m
- WordTraceId: 314043
- atomic: true
- Legal Obligation: unknown
- implement: true
- kind: ordinary

##### A.3.9.2[5] (Requirement Type)
If train length ≤ 900m:
- WordTraceId: 314065
- atomic: true
- Legal Obligation: unknown
- implement: true
- implementerEnhanced: If
  [CONDITION]
  train length ≤ 900m:
- kind: ordinary

##### A.3.9.2[6] (Requirement Type)
a = 3.00
- WordTraceId: 314089
- atomic: true
- Legal Obligation: unknown
- implement: true
- kind: ordinary

##### A.3.9.2[7] (Requirement Type)
b = 2.77
- WordTraceId: 314098
- atomic: true
- Legal Obligation: unknown
- implement: true
- kind: ordinary

##### A.3.9.2[8] (Requirement Type)
c = 0.00
- WordTraceId: 314107
- atomic: true
- Legal Obligation: unknown
- implement: true
- kind: ordinary

##### A.3.9.2[9] (Requirement Type)
If 900m < train length ≤ 1500m:
- WordTraceId: 314116
- atomic: true
- Legal Obligation: unknown
- implement: true
- implementerEnhanced: If
  [CONDITION]
  900m < train length ≤ 1500m:
- kind: ordinary

##### A.3.9.2[10] (Requirement Type)
a = 10.50
- WordTraceId: 314148
- atomic: true
- Legal Obligation: unknown
- implement: true
- kind: ordinary

##### A.3.9.2[11] (Requirement Type)
b = 0.32
- WordTraceId: 314158
- atomic: true
- Legal Obligation: unknown
- implement: true
- kind: ordinary

##### A.3.9.2[12] (Requirement Type)
c = 0.18
- WordTraceId: 314167
- atomic: true
- Legal Obligation: unknown
- implement: true
- kind: ordinary

##### A.3.9.3 (Requirement Type)
A.3.9.3 The basic brake build up time for full service brake for freight trains in G shall be calculated as:
- WordTraceId: 314176
- atomic: true
- Legal Obligation: mandatory
- PlainText: The basic brake build up time for full service brake for freight trains in G shall be calculated as:
- implement: true
- implementerEnhanced: The basic brake build up
  time
  [TIME]
  for full service brake for freight trains in G shall be calculated as:
- kind: ordinary

##### A.3.9.3[2] (Requirement Type)
T_brake_basic_sb = a + b * (L/100) + c * (L/100) 2
- WordTraceId: 314285
- atomic: true
- Legal Obligation: unknown
- PlainText: T_brake_basic_sb = a + b * (L/100) + c * (L/100)2
- implement: true
- kind: ordinary

##### A.3.9.3[3] (Requirement Type)
where
- WordTraceId: 314335
- atomic: true
- Legal Obligation: unknown
- implement: true
- kind: ordinary

##### A.3.9.3[4] (Requirement Type)
L = MAX (400m; train length in m)
- WordTraceId: 314341
- atomic: false
- Legal Obligation: unknown
- implement: true
- kind: ordinary

##### A.3.9.3[5] (Requirement Type)
If train length ≤ 900m:
- WordTraceId: 314375
- atomic: true
- Legal Obligation: unknown
- implement: true
- implementerEnhanced: If
  [CONDITION]
  train length ≤ 900m:
- kind: ordinary

##### A.3.9.3[6] (Requirement Type)
a = 3.00
- WordTraceId: 314399
- atomic: true
- Legal Obligation: unknown
- implement: true
- kind: ordinary

##### A.3.9.3[7] (Requirement Type)
b = 2.77
- WordTraceId: 314408
- atomic: true
- Legal Obligation: unknown
- implement: true
- kind: ordinary

##### A.3.9.3[8] (Requirement Type)
c = 0.00
- WordTraceId: 314417
- atomic: true
- Legal Obligation: unknown
- implement: true
- kind: ordinary

##### A.3.9.3[9] (Requirement Type)
If 900m < train length ≤ 1500m:
- WordTraceId: 314426
- atomic: true
- Legal Obligation: unknown
- implement: true
- implementerEnhanced: If
  [CONDITION]
  900m < train length ≤ 1500m:
- kind: ordinary

##### A.3.9.3[10] (Requirement Type)
a = 10.50
- WordTraceId: 314458
- atomic: true
- Legal Obligation: unknown
- implement: true
- kind: ordinary

##### A.3.9.3[11] (Requirement Type)
b = 0.32
- WordTraceId: 314468
- atomic: true
- Legal Obligation: unknown
- implement: true
- kind: ordinary

##### A.3.9.3[12] (Requirement Type)
c = 0.18
- WordTraceId: 314477
- atomic: true
- Legal Obligation: unknown
- implement: true
- kind: ordinary

##### A.3.9.4 (Requirement Type)
A.3.9.4 The equivalent brake build up time for the service brake shall be computed as follows:
- WordTraceId: 314486
- atomic: true
- Legal Obligation: mandatory
- PlainText: The equivalent brake build up time for the service brake shall be computed as follows:
- implement: true
- implementerEnhanced: The equivalent brake build up
  time
  [TIME]
  for the service brake shall be computed as follows:
- kind: ordinary

##### A.3.9.4[2] (Requirement Type)
T_brake_service_cm0 = T_brake_basic_sb when V_target = 0
- WordTraceId: 314581
- atomic: true
- Legal Obligation: unknown
- implement: true
- implementerEnhanced: T_brake_service_cm0 = T_brake_basic_sb
  when
  [CONDITION]
  V_target = 0
- kind: ordinary

##### A.3.9.4[3] (Requirement Type)
T_brake_service_cmt = kto * T_brake_basic_sb when V_target > 0
- WordTraceId: 314638
- atomic: true
- Legal Obligation: unknown
- implement: true
- implementerEnhanced: T_brake_service_cmt = kto * T_brake_basic_sb
  when
  [CONDITION]
  V_target > 0
- kind: ordinary

##### A.3.9.5 (Requirement Type)
A.3.9.5 The correction factor kto shall be defined as in A.3.8.5
- WordTraceId: 314701
- atomic: true
- Legal Obligation: mandatory
- PlainText: The correction factor kto shall be defined as in A.3.8.5
- implement: false
- kind: Definition
- CrossRefLink -> A.3.8.5

##### A.3.9.6 (Requirement Type)
A.3.9.6 The values of a, b, c and kto used in A.3.9.1, A.3.9.2, A.3.9.3 and A.3.9.4 define reference values for the equivalent brake build up time for the service brake, which shall be considered as maximum ones. If justified by the specific brake system of the train other values of these coefficients, which lead to shorter values of the equivalent brake build up time for the service brake, may be used.
- WordTraceId: 314766
- atomic: false
- Legal Obligation: mixed
- PlainText: The values of a, b, c and kto used in A.3.9.1, A.3.9.2, A.3.9.3 and A.3.9.4 define reference values for the equivalent brake build up time for the service brake, which shall be considered as maximum ones. If justified by the specific brake system of the train other values of these coefficients, which lead to shorter values of the equivalent brake build up time for the service brake, may be used.
- implement: true
- implementerEnhanced: The values of a, b, c and kto used in A.3.9.1, A.3.9.2, A.3.9.3 and A.3.9.4 define reference values for the equivalent brake build up
  time
  [TIME]
  for the service brake, which shall be considered as maximum ones.
  If
  [CONDITION]
  justified by the specific brake system of the train other values of these coefficients, which lead to shorter values of the equivalent brake build up
  time
  [TIME]
  for the service brake, may be used.
- kind: ordinary
- CrossRefLink -> A.3.9.1
- CrossRefLink -> A.3.9.2
- CrossRefLink -> A.3.9.3
- CrossRefLink -> A.3.9.4

##### A.3.9.7 (Requirement Type)
A.3.9.7 Note: Although certain trains may perform better, the reference values for the equivalent brake build up time for the service brake, as defined here, are the appropriate basis for infrastructure planning.
- WordTraceId: 315173
- atomic: false
- Legal Obligation: optional
- PlainText: Note: Although certain trains may perform better, the reference values for the equivalent brake build up time for the service brake, as defined here, are the appropriate basis for infrastructure planning.
- implement: false
- implementerEnhanced: Note: Although certain trains may perform
  better
  [WEAK]
  , the reference values for the equivalent brake build up
  time
  [TIME]
  for the service brake, as defined here, are the appropriate basis for infrastructure planning.
- kind: Note

#### A.3.10 (Requirement Type)
A.3.10 Service brake feedback
- WordTraceId: 315386
- atomic: false
- Legal Obligation: not applicable
- PlainText: Service brake feedback
- implement: false
- implementerEnhanced: Service brake feedback
- kind: Heading

##### A.3.10.1 (Requirement Type)
A.3.10.1 The purpose of service brake feedback is to reduce the distance between the SBI and EBI supervision limits and between the SBI and SBD curves.
- WordTraceId: 315416
- atomic: true
- Legal Obligation: unknown
- PlainText: The purpose of service brake feedback is to reduce the distance between the SBI and EBI supervision limits and between the SBI and SBD curves.
- implement: true
- kind: ordinary

##### A.3.10.2 (Requirement Type)
A.3.10.2 The on-board shall consider the service brake feedback as available for use if:
- WordTraceId: 315568
- atomic: true
- Legal Obligation: mandatory
- PlainText: The on-board shall consider the service brake feedback as available for use if:
- implement: true
- implementerEnhanced: The on-board shall consider the service brake feedback as available for use
  if
  [CONDITION]
  :
- kind: ordinary

###### A.3.10.2.a (Requirement Type)
The service brake feedback is implemented, AND
- WordTraceId: 315657
- atomic: true
- Legal Obligation: mandatory
- implement: true
- ListNumberText: a)
- kind: ordinary

###### A.3.10.2.b (Requirement Type)
The national value does not inhibit its use.
- WordTraceId: 315704
- atomic: true
- Legal Obligation: mandatory
- implement: true
- ListNumberText: b)
- kind: ordinary

##### A.3.10.3 (Requirement Type)
A.3.10.3 Two different types of feedback from the service brake are specified, main brake pipe pressure and brake cylinder pressure. The algorithms below are made for main brake pipe pressure. When brake cylinder pressure is used instead this shall be converted into a fictive main brake pressure value in the following way:
- WordTraceId: 315749
- atomic: false
- Legal Obligation: mandatory
- PlainText: Two different types of feedback from the service brake are specified, main brake pipe pressure and brake cylinder pressure. The algorithms below are made for main brake pipe pressure. When brake cylinder pressure is used instead this shall be converted into a fictive main brake pressure value in the following way:
- implement: true
- implementerEnhanced: Two different types of feedback from the service brake are specified, main brake pipe pressure and brake cylinder pressure. The algorithms
  below
  [WEAK]
  are made for main brake pipe pressure.
  When
  [CONDITION]
  brake cylinder pressure is used instead this shall be converted into a fictive main brake pressure value in the following way:
- kind: ordinary

##### A.3.10.3[2] (Requirement Type)
p = fictive main brake pipe pressure (kPa)
- WordTraceId: 316074
- atomic: true
- Legal Obligation: unknown
- implement: true
- kind: ordinary

##### A.3.10.3[3] (Requirement Type)
p_cylinder = brake cylinder pressure (kPa)
- WordTraceId: 316117
- atomic: true
- Legal Obligation: unknown
- implement: true
- kind: ordinary

##### A.3.10.3[4] (Requirement Type)
k1 = vehicle dependent constant (set by engineering of ETCS on-board; k1 is normally between 2.0 and 2.7)
- WordTraceId: 316160
- atomic: false
- Legal Obligation: unknown
- implement: true
- kind: ordinary

##### A.3.10.3[5] (Requirement Type)
p = 500 - p_cylinder / k1
- WordTraceId: 316266
- atomic: true
- Legal Obligation: unknown
- PlainText: p =  500  - p_cylinder / k1
- implement: true
- kind: ordinary

##### A.3.10.4 (Requirement Type)
A.3.10.4 The value of T_bs1 and T_bs2 shall be calculated according to the following algorithm to take the service brake feedback into account:
- WordTraceId: 316294
- atomic: true
- Legal Obligation: mandatory
- PlainText: The value of T_bs1 and T_bs2 shall be calculated according to the following algorithm to take the service brake feedback into account:
- implement: true
- kind: ordinary

##### A.3.10.4[2] (Requirement Type)
p = current main brake pipe pressure (or fictive main brake pipe pressure calculated in A.3.10.3)
- WordTraceId: 316438
- atomic: true
- Legal Obligation: unknown
- implement: true
- kind: ordinary
- CrossRefLink -> A.3.10.3

##### A.3.10.4[3] (Requirement Type)
p0 = reference pressure when not braking
- WordTraceId: 316536
- atomic: true
- Legal Obligation: unknown
- implement: true
- implementerEnhanced: p0 = reference pressure
  when
  [CONDITION]
  not braking
- kind: ordinary

##### A.3.10.4[4] (Requirement Type)
p1 = pressure at which the train starts to brake = p0 - 30
- WordTraceId: 316578
- atomic: true
- Legal Obligation: unknown
- implement: true
- kind: ordinary

##### A.3.10.4[5] (Requirement Type)
p2 = pressure limit, under which T_bs1 and T_bs2 are locked = p0 - 60
- WordTraceId: 316638
- atomic: true
- Legal Obligation: unknown
- implement: true
- kind: ordinary

##### A.3.10.4[6] (Requirement Type)
p3 = pressure at full service brake = p0 - 150
- WordTraceId: 316709
- atomic: true
- Legal Obligation: unknown
- implement: true
- kind: ordinary

##### A.3.10.4[7] (Requirement Type)
Q_feedback_started = a Boolean stating whether the feedback function has started to reduce T_bs1 and T_bs2.
- WordTraceId: 316757
- atomic: true
- Legal Obligation: unknown
- implement: true
- implementerEnhanced: Q_feedback_started = a Boolean stating
  whether
  [CONDITION]
  the feedback function has started to reduce T_bs1 and T_bs2.
- kind: ordinary

##### A.3.10.4[8] (Requirement Type)
Q_Tbslocked = a boolean stating whether T_bs1 and T_bs2 have been locked to the following values due to enough main brake pipe pressure reduction:
- WordTraceId: 316865
- atomic: true
- Legal Obligation: unknown
- implement: true
- implementerEnhanced: Q_Tbslocked = a boolean stating
  whether
  [CONDITION]
  T_bs1 and T_bs2 have been locked to the following values due to enough main brake pipe pressure reduction:
- kind: ordinary

##### A.3.10.4[9] (Requirement Type)
T_bs1_locked = 0 s.
- WordTraceId: 317012
- atomic: true
- Legal Obligation: unknown
- PlainText: T_bs1_locked =  0 s.
- implement: true
- kind: ordinary

##### A.3.10.4[10] (Requirement Type)
T_bs2_locked = 2 s.
- WordTraceId: 317033
- atomic: true
- Legal Obligation: unknown
- PlainText: T_bs2_locked =  2 s.
- implement: true
- kind: ordinary

##### A.3.10.4[11] (Requirement Type)
If (Q_Tbslocked) or (Q_feedback_started) or (V_est > V_target and the indication supervision limit has been exceeded) then
- WordTraceId: 317055
- atomic: true
- Legal Obligation: unknown
- implement: true
- implementerEnhanced: If
  [CONDITION]
  (Q_Tbslocked) or (Q_feedback_started) or (V_est > V_target and the indication supervision limit has been exceeded) then
- kind: ordinary

##### A.3.10.4[12] (Requirement Type)
If Q_Tbslocked then
- WordTraceId: 317178
- atomic: true
- Legal Obligation: unknown
- implement: true
- implementerEnhanced: If
  [CONDITION]
  Q_Tbslocked then
- kind: ordinary

##### A.3.10.4[13] (Requirement Type)
T_bs1 = T_bs1_locked
- WordTraceId: 317199
- atomic: true
- Legal Obligation: unknown
- implement: true
- kind: ordinary

##### A.3.10.4[14] (Requirement Type)
T_bs2 = T_bs2_locked
- WordTraceId: 317222
- atomic: true
- Legal Obligation: unknown
- implement: true
- kind: ordinary

##### A.3.10.4[15] (Requirement Type)
Else
- WordTraceId: 317245
- atomic: true
- Legal Obligation: unknown
- implement: true
- kind: ordinary

##### A.3.10.4[16] (Requirement Type)
If p > p2 then
- WordTraceId: 317251
- atomic: true
- Legal Obligation: unknown
- implement: true
- implementerEnhanced: If
  [CONDITION]
  p > p2 then
- kind: ordinary

##### A.3.10.4[17] (Requirement Type)
If Q_feedback_started or p ≤ p1 then
- WordTraceId: 317268
- atomic: true
- Legal Obligation: unknown
- implement: true
- implementerEnhanced: If
  [CONDITION]
  Q_feedback_started or p ≤ p1 then
- kind: ordinary

##### A.3.10.4[18] (Requirement Type)
Q_feedback_started = true
- WordTraceId: 317309
- atomic: true
- Legal Obligation: unknown
- implement: true
- kind: ordinary

##### A.3.10.4[19] (Requirement Type)
T_bs_feedback = T_bs * (p - p3) / (p0 - p3)
- WordTraceId: 317339
- atomic: true
- Legal Obligation: unknown
- implement: true
- kind: ordinary

##### A.3.10.4[20] (Requirement Type)
T_bs1 = T_bs2 = T_bs_feedback
- WordTraceId: 317387
- atomic: true
- Legal Obligation: unknown
- implement: true
- kind: ordinary

##### A.3.10.4[21] (Requirement Type)
If T_bs_feedback > T_bs then
- WordTraceId: 317421
- atomic: true
- Legal Obligation: unknown
- implement: true
- implementerEnhanced: If
  [CONDITION]
  T_bs_feedback > T_bs then
- kind: ordinary

##### A.3.10.4[22] (Requirement Type)
T_bs1 = T_bs2 = T_bs
- WordTraceId: 317454
- atomic: true
- Legal Obligation: unknown
- implement: true
- kind: ordinary

##### A.3.10.4[23] (Requirement Type)
Else if T_bs_feedback < T_bs2_locked then
- WordTraceId: 317480
- atomic: true
- Legal Obligation: unknown
- implement: true
- implementerEnhanced: Else
  if
  [CONDITION]
  T_bs_feedback < T_bs2_locked then
- kind: ordinary

##### A.3.10.4[24] (Requirement Type)
T_bs2 = T_bs2_locked
- WordTraceId: 317526
- atomic: true
- Legal Obligation: unknown
- implement: true
- kind: ordinary

##### A.3.10.4[25] (Requirement Type)
End If
- WordTraceId: 317552
- atomic: true
- Legal Obligation: unknown
- implement: true
- implementerEnhanced: End
  If
  [CONDITION]
- kind: ordinary

##### A.3.10.4[26] (Requirement Type)
Else
- WordTraceId: 317563
- atomic: true
- Legal Obligation: unknown
- implement: true
- kind: ordinary

##### A.3.10.4[27] (Requirement Type)
T_bs1 = T_bs
- WordTraceId: 317571
- atomic: true
- Legal Obligation: unknown
- implement: true
- kind: ordinary

##### A.3.10.4[28] (Requirement Type)
T_bs2 = T_bs
- WordTraceId: 317588
- atomic: true
- Legal Obligation: unknown
- implement: true
- kind: ordinary

##### A.3.10.4[29] (Requirement Type)
End If
- WordTraceId: 317605
- atomic: true
- Legal Obligation: unknown
- implement: true
- implementerEnhanced: End
  If
  [CONDITION]
- kind: ordinary

##### A.3.10.4[30] (Requirement Type)
Else
- WordTraceId: 317615
- atomic: true
- Legal Obligation: unknown
- implement: true
- kind: ordinary

##### A.3.10.4[31] (Requirement Type)
T_bs1 = T_bs1_locked
- WordTraceId: 317622
- atomic: true
- Legal Obligation: unknown
- implement: true
- kind: ordinary

##### A.3.10.4[32] (Requirement Type)
T_bs2 = T_bs2_locked
- WordTraceId: 317646
- atomic: true
- Legal Obligation: unknown
- implement: true
- kind: ordinary

##### A.3.10.4[33] (Requirement Type)
Q_Tbslocked = true
- WordTraceId: 317670
- atomic: true
- Legal Obligation: unknown
- implement: true
- kind: ordinary

##### A.3.10.4[34] (Requirement Type)
End If
- WordTraceId: 317692
- atomic: true
- Legal Obligation: unknown
- implement: true
- implementerEnhanced: End
  If
  [CONDITION]
- kind: ordinary

##### A.3.10.4[35] (Requirement Type)
End If
- WordTraceId: 317701
- atomic: true
- Legal Obligation: unknown
- implement: true
- implementerEnhanced: End
  If
  [CONDITION]
- kind: ordinary

##### A.3.10.4[36] (Requirement Type)
Else
- WordTraceId: 317709
- atomic: true
- Legal Obligation: unknown
- implement: true
- kind: ordinary

##### A.3.10.4[37] (Requirement Type)
T_bs1 = T_bs
- WordTraceId: 317714
- atomic: true
- Legal Obligation: unknown
- implement: true
- kind: ordinary

##### A.3.10.4[38] (Requirement Type)
T_bs2 = T_bs
- WordTraceId: 317728
- atomic: true
- Legal Obligation: unknown
- implement: true
- kind: ordinary

##### A.3.10.4[39] (Requirement Type)
End if
- WordTraceId: 317742
- atomic: true
- Legal Obligation: unknown
- implement: true
- implementerEnhanced: End
  if
  [CONDITION]
- kind: ordinary

##### A.3.10.4[40] (Requirement Type)
If (the target speed monitoring is left) or (the target location is passed) then
- WordTraceId: 317751
- atomic: true
- Legal Obligation: unknown
- implement: true
- implementerEnhanced: If
  [CONDITION]
  (the target speed monitoring is left) or (the target location is passed) then
- kind: ordinary

##### A.3.10.4[41] (Requirement Type)
Q_Tbslocked = false
- WordTraceId: 317833
- atomic: true
- Legal Obligation: unknown
- implement: true
- kind: ordinary

##### A.3.10.4[42] (Requirement Type)
Q_feedback_started = false
- WordTraceId: 317854
- atomic: true
- Legal Obligation: unknown
- implement: true
- kind: ordinary

##### A.3.10.4[43] (Requirement Type)
End If
- WordTraceId: 317882
- atomic: true
- Legal Obligation: unknown
- implement: true
- implementerEnhanced: End
  If
  [CONDITION]
- kind: ordinary

##### A.3.10.4[44] (Requirement Type)
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- WordTraceId: 317889
- atomic: true
- Legal Obligation: unknown
- implement: true
- kind: ordinary

##### A.3.10.4[45] (Requirement Type)
The reference pressure p0 (nominal value 500 kPa) shall be set on starting the ETCS:
- WordTraceId: 317919
- atomic: true
- Legal Obligation: mandatory
- implement: true
- kind: ordinary

##### A.3.10.4[46] (Requirement Type)
a) To the first stable p value between 400-550 kPa achieved.
- WordTraceId: 318005
- atomic: true
- Legal Obligation: unknown
- implement: true
- kind: ordinary

##### A.3.10.4[47] (Requirement Type)
b) Stable in this instance means that the pressure has not varied more than ± 20 kPa over 3 seconds.
- WordTraceId: 318068
- atomic: true
- Legal Obligation: unknown
- implement: true
- kind: ordinary

##### A.3.10.4[48] (Requirement Type)
The reference pressure p0 shall thereafter be adapted to the current pressure according to the following table (which applies if the calculation is performed once per second):
- WordTraceId: 318171
- atomic: true
- Legal Obligation: mandatory
- implement: true
- implementerEnhanced: The reference pressure p0 shall thereafter be adapted to the current pressure according to the following table (which applies
  if
  [CONDITION]
  the calculation is performed once per second):
- kind: ordinary

##### A.3.10.4[49] (Requirement Type)
- WordTraceId: 318349
- atomic: false
- Legal Obligation: not applicable
- implement: false
- kind: Placeholder

###### A.3.10.4[49].[t]* (Requirement Type)
| [r][1].[c][1] | [r][1].[c][2] Conditions: | [r][1].[c][3] Action: | [r][1].[c][4] Remarks |
| --- | --- | --- | --- |
| [r][2].[c][1] a) | [r][2].[c][2] p = p0 | [r][2].[c][3] No change | [r][2].[c][4] Constant pressure |
| [r][3].[c][1] b) | [r][3].[c][2] p > p0 | [r][3].[c][3] p0 = p0 + 1,5 | [r][3].[c][4] Increasing pressure |
| [r][4].[c][1] c) | [r][4].[c][2] p < p0 - 30 | [r][4].[c][3] No change | [r][4].[c][4] Braking |
| [r][5].[c][1] d) | [r][5].[c][2] p0 > p > p0 - 30 | [r][5].[c][3] p0 = p0 − 0,5 | [r][5].[c][4] Decreasing pressure |
- WordTraceId: 318553
- atomic: false
- Legal Obligation: not applicable
- implement: false
- kind: Table

###### A.3.10.4[49].[t]*.[r][1] (Requirement Type)
- WordTraceId: 318349
- atomic: false
- Legal Obligation: not applicable
- implement: false
- kind: Table

###### A.3.10.4[49].[t]*.[r][1].[c][1] (Requirement Type)
- WordTraceId: 318349
- atomic: true
- Legal Obligation: unknown
- implement: true
- kind: ordinary

###### A.3.10.4[49].[t]*.[r][1].[c][2] (Requirement Type)
Conditions:
- WordTraceId: 318350
- atomic: true
- Legal Obligation: unknown
- PlainText: CONDITIONS:
- implement: true
- implementerEnhanced: CONDITIONS:
- kind: ordinary

###### A.3.10.4[49].[t]*.[r][1].[c][3] (Requirement Type)
Action:
- WordTraceId: 318362
- atomic: true
- Legal Obligation: unknown
- PlainText: ACTION:
- implement: true
- implementerEnhanced: ACTION:
- kind: ordinary

###### A.3.10.4[49].[t]*.[r][1].[c][4] (Requirement Type)
Remarks
- WordTraceId: 318370
- atomic: true
- Legal Obligation: unknown
- PlainText: REMARKS
- implement: true
- implementerEnhanced: REMARKS
- kind: ordinary

###### A.3.10.4[49].[t]*.[r][2] (Requirement Type)
- WordTraceId: 318379
- atomic: false
- Legal Obligation: not applicable
- implement: false
- kind: Table

###### A.3.10.4[49].[t]*.[r][2].[c][1] (Requirement Type)
a)
- WordTraceId: 318379
- atomic: true
- Legal Obligation: unknown
- implement: true
- kind: ordinary

###### A.3.10.4[49].[t]*.[r][2].[c][2] (Requirement Type)
p = p0
- WordTraceId: 318382
- atomic: true
- Legal Obligation: unknown
- implement: true
- kind: ordinary

###### A.3.10.4[49].[t]*.[r][2].[c][3] (Requirement Type)
No change
- WordTraceId: 318389
- atomic: true
- Legal Obligation: unknown
- implement: true
- kind: ordinary

###### A.3.10.4[49].[t]*.[r][2].[c][4] (Requirement Type)
Constant pressure
- WordTraceId: 318399
- atomic: true
- Legal Obligation: unknown
- implement: true
- kind: ordinary

###### A.3.10.4[49].[t]*.[r][3] (Requirement Type)
- WordTraceId: 318418
- atomic: false
- Legal Obligation: not applicable
- implement: false
- kind: Table

###### A.3.10.4[49].[t]*.[r][3].[c][1] (Requirement Type)
b)
- WordTraceId: 318418
- atomic: true
- Legal Obligation: unknown
- implement: true
- kind: ordinary

###### A.3.10.4[49].[t]*.[r][3].[c][2] (Requirement Type)
p > p0
- WordTraceId: 318421
- atomic: true
- Legal Obligation: unknown
- implement: true
- kind: ordinary

###### A.3.10.4[49].[t]*.[r][3].[c][3] (Requirement Type)
p0 = p0 + 1,5
- WordTraceId: 318428
- atomic: true
- Legal Obligation: unknown
- implement: true
- kind: ordinary

###### A.3.10.4[49].[t]*.[r][3].[c][4] (Requirement Type)
Increasing pressure
- WordTraceId: 318442
- atomic: true
- Legal Obligation: unknown
- implement: true
- kind: ordinary

###### A.3.10.4[49].[t]*.[r][4] (Requirement Type)
- WordTraceId: 318463
- atomic: false
- Legal Obligation: not applicable
- implement: false
- kind: Table

###### A.3.10.4[49].[t]*.[r][4].[c][1] (Requirement Type)
c)
- WordTraceId: 318463
- atomic: true
- Legal Obligation: unknown
- implement: true
- kind: ordinary

###### A.3.10.4[49].[t]*.[r][4].[c][2] (Requirement Type)
p < p0 - 30
- WordTraceId: 318466
- atomic: true
- Legal Obligation: unknown
- implement: true
- kind: ordinary

###### A.3.10.4[49].[t]*.[r][4].[c][3] (Requirement Type)
No change
- WordTraceId: 318478
- atomic: true
- Legal Obligation: unknown
- implement: true
- kind: ordinary

###### A.3.10.4[49].[t]*.[r][4].[c][4] (Requirement Type)
Braking
- WordTraceId: 318488
- atomic: true
- Legal Obligation: unknown
- implement: true
- kind: ordinary

###### A.3.10.4[49].[t]*.[r][5] (Requirement Type)
- WordTraceId: 318497
- atomic: false
- Legal Obligation: not applicable
- implement: false
- kind: Table

###### A.3.10.4[49].[t]*.[r][5].[c][1] (Requirement Type)
d)
- WordTraceId: 318497
- atomic: true
- Legal Obligation: unknown
- implement: true
- kind: ordinary

###### A.3.10.4[49].[t]*.[r][5].[c][2] (Requirement Type)
p0 > p
>
p0
- 30
- WordTraceId: 318500
- atomic: true
- Legal Obligation: unknown
- PlainText: p0 > p > p0 - 30
- implement: true
- implementerEnhanced: p0 > p > p0 - 30
- kind: ordinary

###### A.3.10.4[49].[t]*.[r][5].[c][3] (Requirement Type)
p0 = p0
−
0,5
- WordTraceId: 318517
- atomic: true
- Legal Obligation: unknown
- PlainText: p0 = p0 − 0,5
- implement: true
- implementerEnhanced: p0 = p0 − 0,5
- kind: ordinary

###### A.3.10.4[49].[t]*.[r][5].[c][4] (Requirement Type)
Decreasing pressure
- WordTraceId: 318531
- atomic: true
- Legal Obligation: unknown
- implement: true
- kind: ordinary

##### A.3.10.4[50] (Requirement Type)
Where:
- WordTraceId: 318553
- atomic: true
- Legal Obligation: unknown
- implement: true
- kind: ordinary

##### A.3.10.4[51] (Requirement Type)
- p is limited to max 550 kPa.
- WordTraceId: 318561
- atomic: true
- Legal Obligation: unknown
- implement: true
- kind: ordinary

##### A.3.10.4[52] (Requirement Type)
- Values given in kPa.
- WordTraceId: 318592
- atomic: true
- Legal Obligation: unknown
- implement: true
- kind: ordinary

##### A.3.10.5 (Requirement Type)
A.3.10.5 Note: If T_bs1 and T_bs2 have been locked to 0s and 2 s, the locking will remain until the target speed monitoring is left, even if the train speed comes below the target speed. This avoids “jumping” indications. It also makes it possible to release the brakes before a speed reduction, without having the curves moving back again. It might though result in emergency brake intervention if the driver releases the brakes too early. But since EBI is not moved, this is not a safety issue. To keep 2 s between the SBI and EBI enables the service brake to be activated first and thus may avoid emergency brake.
- WordTraceId: 318616
- atomic: false
- Legal Obligation: optional
- PlainText: Note: If T_bs1 and T_bs2 have been locked to 0s and 2 s, the locking will remain until the target speed monitoring is left, even if the train speed comes below the target speed. This avoids “jumping” indications. It also makes it possible to release the brakes before a speed reduction, without having the curves moving back again. It might though result in emergency brake intervention if the driver releases the brakes too early. But since EBI is not moved, this is not a safety issue. To keep 2 s between the SBI and EBI enables the service brake to be activated first and thus may avoid emergency brake.
- implement: false
- implementerEnhanced: Note:
  If
  [CONDITION]
  T_bs1 and T_bs2 have been locked to 0s and 2 s, the locking will remain
  until
  [TIME]
  the target speed monitoring is left,
  even
  if
  [CONDITION]
  [WEAK]
  the train speed comes
  below
  [WEAK]
  the target speed. This avoids “jumping” indications. It also makes it possible to release the brakes before a speed reduction, without having the curves moving back
  again
  [LOOP]
  . It might though result in emergency brake intervention
  if
  [CONDITION]
  the
  driver
  [EXTERNAL]
  releases the brakes too early. But since EBI is not moved, this is not a safety issue. To keep 2 s between the SBI and EBI enables the service brake to be activated first and thus may avoid emergency brake.
- kind: Note

##### A.3.10.6 (Requirement Type)
A.3.10.6 Note: If feedback has started but T_bs1 and T_bs2 are not locked, the feedback function will remain active until the target point is reached. This avoids “jumping” indications in some rare situations.
- WordTraceId: 319233
- atomic: false
- Legal Obligation: not applicable
- PlainText: Note: If feedback has started but T_bs1 and T_bs2 are not locked, the feedback function will remain active until the target point is reached. This avoids “jumping” indications in some rare situations.
- implement: false
- implementerEnhanced: Note:
  If
  [CONDITION]
  feedback has started but T_bs1 and T_bs2 are not locked, the feedback function will remain active
  until
  [TIME]
  the target point is reached. This avoids “jumping” indications in some rare situations.
- kind: Note

## 4.8 (Proxy Type)

## 5.17 (Proxy Type)

## 5.16.3 (Proxy Type)

## 4.11 (Proxy Type)

## 4.10 (Proxy Type)

## 4.6.1 (Proxy Type)

## 5.10 (Proxy Type)

## 5.8.4.1.c (Proxy Type)

## 5.8.3.1.3 (Proxy Type)

## 1.1 (Proxy Type)
