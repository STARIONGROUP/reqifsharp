# IBM Rational DOORS, 15 June 2022

# Specification: JM616_ADS制御

## 1
- JTEKT_ID: 6

## 2
- JTEKT_ID: 7

## 3
- JTEKT_ID: 518

## 4
- JTEKT_ID: 532

## 5
- JTEKT_ID: 534

## 27
- JTEKT_ID: 6510

### 28
- JTEKT_ID: 6511

#### 29
- JTEKT_ID: 6512

#### 30
- JTEKT_ID: 6516

#### 31
- JTEKT_ID: 6519

#### 32
- JTEKT_ID: 6517

#### 33
- JTEKT_ID: 6518

#### 34
- JTEKT_ID: 6520

#### 35
- JTEKT_ID: 6527

### 36
- JTEKT_ID: 6513

#### 37
- JTEKT_ID: 6515

### 38
- JTEKT_ID: 6521

#### 39
- JTEKT_ID: 6522

#### 40
- JTEKT_ID: 6523

#### 41
- JTEKT_ID: 6524

#### 42
- JTEKT_ID: 6525

#### 43
- JTEKT_ID: 6526

# Specification: JM616_ADS制御2

## 24
- JTEKT_ID: 5200

## 25
- JTEKT_ID: 6049

## 26
- JTEKT_ID: 6186

## 44
- JTEKT_ID: 6528

### 45
- JTEKT_ID: 6529

#### 46
- JTEKT_ID: 6530

#### 47
- JTEKT_ID: 6531

#### 48
- JTEKT_ID: 6532

#### 49
- JTEKT_ID: 6545

#### 50
- JTEKT_ID: 6547

#### 51
- JTEKT_ID: 6535

#### 52
- JTEKT_ID: 6546

#### 53
- JTEKT_ID: 6536

#### 54
- JTEKT_ID: 6548

### 55
- JTEKT_ID: 6537

#### 56
- JTEKT_ID: 6538

### 57
- JTEKT_ID: 6539

#### 58
- JTEKT_ID: 6540

#### 59
- JTEKT_ID: 6541

#### 60
- JTEKT_ID: 6542

#### 61
- JTEKT_ID: 6543

#### 62
- JTEKT_ID: 6544

## 63
- JTEKT_ID: 6050

## 6
- JTEKT_ID: 536

## 7
- JTEKT_ID: 540

## 8
- JTEKT_ID: 1004

## 9
- JTEKT_ID: 4534

## 10
- JTEKT_ID: 4560

## 11
- JTEKT_ID: 648

## 12
- JTEKT_ID: 977

## 13
- JTEKT_ID: 815

## 14
- JTEKT_ID: 4806

## 15
- JTEKT_ID: 1119

## 16
- JTEKT_ID: 1215

## 17
- JTEKT_ID: 722

## 18
- JTEKT_ID: 2309

## 19
- JTEKT_ID: 6001

## 20
- JTEKT_ID: 5288

## 21
- JTEKT_ID: 1670

## 22
- JTEKT_ID: 2189

## 23
- JTEKT_ID: 4867
