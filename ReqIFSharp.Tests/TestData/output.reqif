# this is a title
this is a comment

# Specification: specification 1
- boolean attribute: true
- date attribute: 2015-12-01T00:00:00.0000000
- enumeration attribute: low
- integer attribute: 1
- real attribute: 100
- string attribute: a string value

## specobject_1: spec object 1
- boolean attribute: true
- date attribute: 2015-12-01T00:00:00.0000000
- enumeration attribute: low
- integer attribute: 1
- real attribute: 100
- string attribute: a string value
- xhtml attribute: The mission duration shall not exceed 3 months from launch.
- Specification Relation Type -> specobject_2
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
### specobject_2: spec object 2
- boolean attribute: true
- date attribute: 2015-12-01T00:00:00.0000000
- enumeration attribute: low
- integer attribute: 1
- real attribute: 100
- string attribute: a string value

### specobject_3: spec object 3
- boolean attribute: true
- date attribute: 2015-12-01T00:00:00.0000000
- enumeration attribute: low
- integer attribute: 1
- real attribute: 100
- string attribute: a string value

# Specification: specification 2
- boolean attribute: true
- date attribute: 2015-12-01T00:00:00.0000000
- enumeration attribute: low
- integer attribute: 1
- real attribute: 100
- string attribute: a string value
