# Specification Title

# Specification: Specification Document
- Description: Requirements Document

## R1
- This is the demo file that resulted from the Datatype configuration lecture at ReqIF.academy
- 10
- REQ-1
- true
- 2017-01-01T13:00:00.000+01:00
- , , Three
- Embedded Image:
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
## R2
This SpecObject has a different type than the others.

## R3
- REQ-2
- This SpecType is associated with an ID generator.
- Embedded File:
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