# Example ReqIF file
Optional comment associated with the Exchange Document as a whole

# Specification: Forest Fire Detection System

## R001: Observe earths surface. (Functional Requirement)
- The system shall observe the earths surface.
- Description of the SpecObject that includes formatted tables and/or style:
  - Element 1
  - Element 2

## R002: Spotting fire (Functional Requirement)
- The system shall alert the control center if it spots a fire in a forest.

## R003: Fast system (Performance Requirement)
- The time span between detection of a fire and alerting of control center shall be less than 3 sec.
