# Traceability Template
Download this template and others at https://reqif.academy

# Specification: Requirements Document
- ReqIF.Name: Stakeholder Requirements

## REQ-1: Stakeholder Requirements

### REQ-21
Download this template and more at reqif.academy

### REQ-2
This is a simple template that demonstrates the traceability capabilities of ReqIF Studio.

### REQ-6
Simply delete these instructions in the Stakeholder Requirements and System Requirements, and you are good to go.

## REQ-7: Traceability Basics

### REQ-3
You can quickly recognize whether outgoing traces exist by looking into the right-most column (called Link).

### REQ-8
Example: The following depicts one incoming and two outoging links:
1 ▷ Ⓡ ▷ 2

### REQ-9
Traces are by default folded in. To see them, either (1) double-click on the symbol in the link column, or (2) use the toolbar button to unfold all links.

## REQ-4: Change Management

### REQ-5
Further, this ReqIF file is configured for change management. The SpecRelations (traces) contain a flag, indicating whether source or target has changed.

### REQ-10
You can reset the flag by double-clicking on the warning sign ⚠

### REQ-11
As soon as any attribute of the source or target changes, the warning flag is set again.

### REQ-12
You can also manually set the flag by double-clicking the link's attribute.

# Specification
- ReqIF.Name: System Requirements

## REQ-13: System Requirements

### REQ-14
You can use this document (Specification) to record your system requirements.

### REQ-15
To demonstrate the traceability feature, you find counterparts to the elements in the Stakeholder Requirements here.

### REQ-16
To use this template, simply delete them.

## REQ-17: Link Elements (for demonstration)

### REQ-18
Explain the use of the template
- realizes -> REQ-2
- realizes -> REQ-6

### REQ-19
Explain the GUI elements.
- realizes -> REQ-8
- realizes -> REQ-3
- realizes -> REQ-9

### REQ-20
Explain the Traceability Presentation's functionality.
- realizes -> REQ-10
- realizes -> REQ-5
- realizes -> REQ-12
- realizes -> REQ-11
